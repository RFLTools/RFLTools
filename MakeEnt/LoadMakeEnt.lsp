(setq RFL:MAKEENTBLOCKLIST (list 
                                 "ALTABLE01" 
                                 "ALTABLE01DATA" 
                                 "BCCURVETABLE" 
                                 "BCCURVETABLEDATA" 
                                 "CIRC" 
                                 "CURVETABLE" 
                                 "CURVETABLEDATA" 
                                 "DRAWGRIDDEF" 
                                 "FORCE" 
                                 "LKI" 
                                 "LTESTTRAINSECTION" 
                                 "LTRAINSECTION" 
                                 "PLACEMARKPOINT" 
                                 "POINT" 
                                 "PPSLOPE" 
                                 "PR-CIRCLE" 
                                 "PVI2" 
                                 "RFLALIGN" 
                                 "RFLPROF" 
                                 "RFLPROFVOLNODE" 
                                 "RFLSURVEY" 
                                 "RFLTRAIN" 
                                 "ROUNDABOUT" 
                                 "RTESTTRAINSECTION" 
                                 "RTRAINSECTION" 
                                 "SECT-REF" 
                                 "SPOTELEVATION" 
                                 "SPOTELEVATION2" 
                                 "STALBL" 
                                 "STANODELEFT" 
                                 "STANODERIGHT" 
                                 "STATICK" 
                                 "SUPER" 
                                 "SURVEYSPOT" 
                                 "TESTTRAINSECTION" 
                                 "TRAINSECTION" 
                           ) 
) 
;
;
;     Program written by Robert Livingston, 02-10-21
;
;     MAKEENT is a utility for creating RFL blocks within lisp
;
;
(defun C:MAKEENT (/ DCL_ID ACCEPTMAKEENT BLOCKINDEX CANCELMAKEENT UPDATEBLOCK)
 (defun ACCEPTMAKEENT (/ C)
  (RFL:MAKEENT (nth BLOCKINDEX RFL:MAKEENTBLOCKLIST))
  (setq BLOCKINDEX nil)
  (done_dialog)
  (unload_dialog DCL_ID)
 )
 (defun CANCELMAKEENT ()
  (setq BLOCKINDEX nil)
  (done_dialog)
  (unload_dialog DCL_ID)
 )

 (defun UPDATEBLOCK ()
  (setq BLOCKINDEX (atoi (get_tile "BLOCKNAME")))
  (done_dialog)
  (unload_dialog DCL_ID)
 )

 (setq BLOCKINDEX 0)

 (while (/= nil BLOCKINDEX)
  (if (= MAKEENTDCLNAME nil)
   (progn
    (setq MAKEENTDCLNAME (vl-filename-mktemp "rfl.dcl"))
    (RFL:MAKEDCL MAKEENTDCLNAME "MAKEENT")
   )
   (if (= nil (findfile MAKEENTDCLNAME))
    (progn
     (setq MAKEENTDCLNAME (vl-filename-mktemp "rfl.dcl"))
     (RFL:MAKEDCL MAKEENTDCLNAME "MAKEENT")
    )
   )
  )
  (setq DCL_ID (load_dialog MAKEENTDCLNAME))
  (if (not (new_dialog "MAKEENT" DCL_ID)) (exit))

  (start_list "BLOCKNAME")
  (mapcar 'add_list RFL:MAKEENTBLOCKLIST)
  (end_list)

  (set_tile "BLOCKNAME" (itoa BLOCKINDEX))

  (setq RFLALIGNSLBNAME "rflAlign.slb")
  (if (= nil (findfile RFLALIGNSLBNAME))
   (progn
    (setq RFLALIGNSLBNAME (vl-filename-mktemp "rfl.slb"))
    (RFL:MAKERFLSLB RFLALIGNSLBNAME)
   )
  )
  (start_image "IMAGE")
  (slide_image 0 0 (- (dimx_tile "IMAGE") 1)
                   (- (dimy_tile "IMAGE") 1)
                   (strcat RFLALIGNSLBNAME "(" (nth BLOCKINDEX RFL:MAKEENTBLOCKLIST) ")")
  )
  (end_image)

  (action_tile "BLOCKNAME" "(UPDATEBLOCK)")
  (action_tile "OK" "(ACCEPTMAKEENT)")
  (action_tile "CANCEL" "(CANCELMAKEENT)")

  (start_dialog)
 )
)
;
;
;     Program written by Robert Livingston, 02-10-21
;
;     RFL:MAKEENT cycles through the block list returned by RFL:GETBLOCKLIST creating the block
;
;
(defun RFL:MAKEENT (BLKNAME / BLOCKLIST NODE)
 (setq BLOCKLIST (RFL:GETBLOCKLIST BLKNAME))
 (if (/= nil BLOCKLIST)
  (progn
   (entmake)
   (foreach NODE BLOCKLIST
    (entmake NODE)
   )
  )
  nil
 )
)
(defun RFL:GETBLOCKLIST (BLKNAME)
 (cond
       ((= (strcase BLKNAME) "ALTABLE01")
        (list
         (list
          (cons 0 "BLOCK")
          (cons 2 "ALTable01")
          (cons 70  2)
          (cons 4 "")
          (list 10 0.00000000 0.00000000 0.00000000)
         )
         (list
          (cons 0 "ATTDEF")
          (cons 100 "AcDbEntity")
          (cons 67 0)
          (cons 8 "0")
          (cons 62 2)
          (cons 100 "AcDbText")
          (list 10 54.29019558 -4.83819420 0.00000000)
          (cons 40  3.00000000)
          (cons 1 "")
          (cons 50  0.00000000)
          (cons 41  0.90000000)
          (cons 51  0.00000000)
          (cons 7 "Standard")
          (cons 71 0)
          (cons 72 4)
          (list 11 54.29019558 -4.83819420 0.00000000)
          (list 210 0.00000000 0.00000000 1.00000000)
          (cons 100 "AcDbAttributeDefinition")
          (cons 280 0)
          (cons 3 "Title")
          (cons 2 "TITLE")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 -3.91428571 -22.40000000 0.00000000)
          (cons 40  1.00000000)
          (cons 1 "23.4")
          (cons 50  0.00000000)
          (cons 41  0.90000000)
          (cons 51  0.00000000)
          (cons 7 "Standard")
          (cons 71 0)
          (cons 72 2)
          (list 11 -1.00000000 -22.40000000 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 3)
          (cons 100 "AcDbLine")
          (list 10 0.00000000 -9.66445149 0.00000000)
          (list 11 108.94986374 -9.66445148 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -23.40000000 0.00000000)
          (list 11 108.94986374 -23.39999997 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 0.00000000 0.00000000)
          (list 11 108.94986374 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 19.65708710 -23.39999999 0.00000000)
          (list 11 19.65708710 -9.66445148 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 -23.40000000 0.00000000)
          (list 11 0.00000000 0.00000000 0.00000000)
          (list 210 0.00000000 0.00000000 1.00000000)
         )
         (list
          (cons 0 "TEXT")
          (cons 100 "AcDbEntity")
          (cons 67 0)
          (cons 8 "0")
          (cons 62 2)
          (cons 100 "AcDbText")
          (list 10 26.76456700 -14.77855408 0.00000000)
          (cons 40  3.00000000)
          (cons 1 "STATION")
          (cons 50  0.00000000)
          (cons 41  0.90000000)
          (cons 51  0.00000000)
          (cons 7 "Standard")
          (cons 71 0)
          (cons 72 4)
          (list 11 34.54313843 -13.27855408 0.00000000)
          (list 210 0.00000000 0.00000000 1.00000000)
          (cons 100 "AcDbText")
          (cons 73 0)
         )
         (list
          (cons 0 "LINE")
          (cons 100 "AcDbEntity")
          (cons 67 0)
          (cons 8 "0")
          (cons 62 3)
          (cons 100 "AcDbLine")
          (list 10 108.94986374 -23.39999997 0.00000000)
          (list 11 108.94986374 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 49.42134598 -23.39999999 0.00000000)
          (list 11 49.42134598 -9.66445148 0.00000000)
          (list 210 0.00000000 0.00000000 1.00000000)
         )
         (list
          (cons 0 "LINE")
          (cons 100 "AcDbEntity")
          (cons 67 0)
          (cons 8 "0")
          (cons 62 1)
          (cons 100 "AcDbLine")
          (list 10 49.42134598 -16.63964179 0.00000000)
          (list 11 108.94986374 -16.63964178 0.00000000)
          (list 210 0.00000000 0.00000000 1.00000000)
         )
         (list
          (cons 0 "TEXT")
          (cons 100 "AcDbEntity")
          (cons 67 0)
          (cons 8 "0")
          (cons 62 2)
          (cons 100 "AcDbText")
          (list 10 57.68204685 -21.65607812 0.00000000)
          (cons 40  3.00000000)
          (cons 1 "NORTH")
          (cons 50  0.00000000)
          (cons 41  0.90000000)
          (cons 51  0.00000000)
          (cons 7 "Standard")
          (cons 71 0)
          (cons 72 4)
          (list 11 64.30347542 -20.15607812 0.00000000)
          (list 210 0.00000000 0.00000000 1.00000000)
          (cons 100 "AcDbText")
          (cons 73 0)
         )
         (list
          (cons 0 "LINE")
          (cons 100 "AcDbEntity")
          (cons 67 0)
          (cons 8 "0")
          (cons 62 1)
          (cons 100 "AcDbLine")
          (list 10 79.18560486 -23.39999998 0.00000000)
          (list 11 79.18560486 -16.63964178 0.00000000)
          (list 210 0.00000000 0.00000000 1.00000000)
         )
         (list
          (cons 0 "TEXT")
          (cons 100 "AcDbEntity")
          (cons 67 0)
          (cons 8 "0")
          (cons 62 2)
          (cons 100 "AcDbText")
          (list 10 89.18202001 -21.65607812 0.00000000)
          (cons 40  3.00000000)
          (cons 1 "EAST")
          (cons 50  0.00000000)
          (cons 41  0.90000000)
          (cons 51  0.00000000)
          (cons 7 "Standard")
          (cons 71 0)
          (cons 72 4)
          (list 11 94.06773430 -20.15607812 0.00000000)
          (list 210 0.00000000 0.00000000 1.00000000)
          (cons 100 "AcDbText")
          (cons 73 0)
         )
         (list
          (cons 0 "TEXT")
          (cons 100 "AcDbEntity")
          (cons 67 0)
          (cons 8 "0")
          (cons 62 2)
          (cons 100 "AcDbText")
          (list 10 65.68560485 -14.77855408 0.00000000)
          (cons 40  3.00000000)
          (cons 1 "COORDINATES")
          (cons 50  0.00000000)
          (cons 41  0.90000000)
          (cons 51  0.00000000)
          (cons 7 "Standard")
          (cons 71 0)
          (cons 72 4)
          (list 11 79.18560485 -13.27855408 0.00000000)
          (list 210 0.00000000 0.00000000 1.00000000)
          (cons 100 "AcDbText")
          (cons 73 0)
         )
         (list (cons 0 "ENDBLK"))
        )
       )
       ((= (strcase BLKNAME) "ALTABLE01DATA")
        (list
         (list
          (cons 0 "BLOCK")
          (cons 2 "altable01data")
          (cons 70  2)
          (list 10 0.00000000 0.00000000 0.00000000)
         )
         (list
          (cons 0 "ATTDEF")
          (cons 100 "AcDbEntity")
          (cons 67 0)
          (cons 8 "0")
          (cons 62 1)
          (cons 100 "AcDbText")
          (list 10 9.74777432 -3.00000000 0.00000000)
          (cons 40  2.50000000)
          (cons 1 "")
          (cons 50  0.00000000)
          (cons 41  0.90000000)
          (cons 51  0.00000000)
          (cons 7 "Standard")
          (cons 71 0)
          (cons 72 4)
          (list 11 9.74777432 -3.00000000 0.00000000)
          (list 210 0.00000000 0.00000000 1.00000000)
          (cons 100 "AcDbAttributeDefinition")
          (cons 280 0)
          (cons 3 "Point Number")
          (cons 2 "PNT")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 34.45844733 -3.00000000 0.00000000)
          (cons 40  2.50000000)
          (cons 1 "")
          (cons 50  0.00000000)
          (cons 41  0.90000000)
          (cons 51  0.00000000)
          (cons 7 "Standard")
          (cons 71 0)
          (cons 72 4)
          (list 11 34.45844733 -3.00000000 0.00000000)
          (list 210 0.00000000 0.00000000 1.00000000)
          (cons 100 "AcDbAttributeDefinition")
          (cons 280 0)
          (cons 3 "Station")
          (cons 2 "STA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 64.22270621 -3.00000000 0.00000000)
          (cons 40  2.50000000)
          (cons 1 "")
          (cons 50  0.00000000)
          (cons 41  0.90000000)
          (cons 51  0.00000000)
          (cons 7 "Standard")
          (cons 71 0)
          (cons 72 4)
          (list 11 64.22270621 -3.00000000 0.00000000)
          (list 210 0.00000000 0.00000000 1.00000000)
          (cons 100 "AcDbAttributeDefinition")
          (cons 280 0)
          (cons 3 "Northing")
          (cons 2 "NORTHING")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 93.98696509 -3.00000000 0.00000000)
          (cons 40  2.50000000)
          (cons 1 "")
          (cons 50  0.00000000)
          (cons 41  0.90000000)
          (cons 51  0.00000000)
          (cons 7 "Standard")
          (cons 71 0)
          (cons 72 4)
          (list 11 93.98696509 -3.00000000 0.00000000)
          (list 210 0.00000000 0.00000000 1.00000000)
          (cons 100 "AcDbAttributeDefinition")
          (cons 280 0)
          (cons 3 "Easting")
          (cons 2 "EASTING")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 -3.01428571 -5.00000000 0.00000000)
          (cons 40  1.00000000)
          (cons 1 "6.0")
          (cons 50  0.00000000)
          (cons 41  0.90000000)
          (cons 51  0.00000000)
          (cons 7 "Standard")
          (cons 71 0)
          (cons 72 2)
          (list 11 -1.00000000 -5.00000000 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 3)
          (cons 100 "AcDbLine")
          (list 10 0.00000000 -6.00000000 0.00000000)
          (list 11 0.00000000 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 19.65708710 -6.00000000 0.00000000)
          (list 11 19.65708710 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 49.42134598 -6.00000000 0.00000000)
          (list 11 49.42134598 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 79.18560486 -6.00000000 0.00000000)
          (list 11 79.18560486 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 108.94986374 -6.00000000 0.00000000)
          (list 11 108.94986374 0.00000000 0.00000000)
          (list 210 0.00000000 0.00000000 1.00000000)
         )
         (list (cons 0 "ENDBLK"))
        )
       )
       ((= (strcase BLKNAME) "BCCURVETABLE")
        (list
         (list
          (cons 0 "BLOCK")
          (cons 2 "BCCurveTable")
          (cons 70  2)
          (list 10 0.00000000 0.00000000 0.00000000)
         )
         (list
          (cons 0 "LINE")
          (cons 100 "AcDbEntity")
          (cons 67 0)
          (cons 8 "0")
          (cons 62 30)
          (cons 100 "AcDbLine")
          (list 10 7.00000000 -33.99600000 0.00000000)
          (list 11 0.00000000 -33.99600000 0.00000000)
          (list 210 0.00000000 0.00000000 1.00000000)
         )
         (list
          (cons 0 "LWPOLYLINE")
          (cons 100 "AcDbEntity")
          (cons 67 0)
          (cons 8 "0")
          (cons 62 3)
          (cons 100 "AcDbPolyline")
          (cons 90 4)
          (cons 70 128)
          (cons 43  0.00000000)
          (cons 38  0.00000000)
          (cons 39  0.00000000)
          (list 10 7.00000000 0.00000000)
          (cons 40  0.00000000)
          (cons 41  0.00000000)
          (cons 42  0.00000000)
          (cons 91 0)
          (list 10 0.00000000 0.00000000)
          (cons 40  0.00000000)
          (cons 41  0.00000000)
          (cons 42  0.00000000)
          (cons 91 0)
          (list 10 0.00000000 -45.32800000)
          (cons 40  0.00000000)
          (cons 41  0.00000000)
          (cons 42  0.00000000)
          (cons 91 0)
          (list 10 7.00000000 -45.32799986)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 62 3)
          (cons 100 "AcDbLine")
          (list 10 7.00000000 -2.83300000 0.00000000)
          (list 11 0.00000000 -2.83300000 0.00000000)
          (list 210 0.00000000 0.00000000 1.00000000)
         )
         (list
          (cons 0 "LWPOLYLINE")
          (cons 100 "AcDbEntity")
          (cons 67 0)
          (cons 8 "0")
          (cons 100 "AcDbPolyline")
          (cons 90 3)
          (cons 70 1)
          (cons 43  0.00000000)
          (cons 38  0.00000000)
          (cons 39  0.00000000)
          (list 10 2.40507917 -9.29116667)
          (cons 40  0.00000000)
          (cons 41  0.00000000)
          (cons 42  0.00000000)
          (cons 91 0)
          (list 10 3.03007917 -10.54116667)
          (cons 40  0.00000000)
          (cons 41  0.00000000)
          (cons 42  0.00000000)
          (cons 91 0)
          (list 10 1.78007917 -10.54116667)
          (cons 40  0.00000000)
          (cons 41  0.00000000)
          (cons 42  0.00000000)
          (cons 91 0)
          (list 210 0.00000000 0.00000000 1.00000000)
         )
         (list
          (cons 0 "LWPOLYLINE")
          (cons 100 "AcDbEntity")
          (cons 67 0)
          (cons 8 "0")
          (cons 100 "AcDbPolyline")
          (cons 90 3)
          (cons 70 1)
          (cons 43  0.00000000)
          (cons 38  0.00000000)
          (cons 39  0.00000000)
          (list 10 2.40507917 -6.45783333)
          (cons 40  0.00000000)
          (cons 41  0.00000000)
          (cons 42  0.00000000)
          (cons 91 0)
          (list 10 3.03007917 -7.70783333)
          (cons 40  0.00000000)
          (cons 41  0.00000000)
          (cons 42  0.00000000)
          (cons 91 0)
          (list 10 1.78007917 -7.70783333)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 62 30)
          (cons 100 "AcDbLine")
          (list 10 7.00000000 -5.66600000 0.00000000)
          (list 11 0.00000000 -5.66600000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -8.49900000 0.00000000)
          (list 11 0.00000000 -8.49900000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -11.33200000 0.00000000)
          (list 11 0.00000000 -11.33200000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -16.99800000 0.00000000)
          (list 11 0.00000000 -16.99800000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -19.83100000 0.00000000)
          (list 11 0.00000000 -19.83100000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -22.66400000 0.00000000)
          (list 11 0.00000000 -22.66400000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -31.16300000 0.00000000)
          (list 11 0.00000000 -31.16300000 0.00000000)
          (list 210 0.00000000 0.00000000 1.00000000)
         )
         (list
          (cons 0 "LINE")
          (cons 100 "AcDbEntity")
          (cons 67 0)
          (cons 8 "0")
          (cons 62 3)
          (cons 100 "AcDbLine")
          (list 10 7.00000000 -36.82900000 0.00000000)
          (list 11 0.00000000 -36.82900000 0.00000000)
          (list 210 0.00000000 0.00000000 1.00000000)
         )
         (list
          (cons 0 "TEXT")
          (cons 100 "AcDbEntity")
          (cons 67 0)
          (cons 8 "0")
          (cons 100 "AcDbText")
          (list 10 2.83169909 -10.54155327 0.00000000)
          (cons 40  1.25000000)
          (cons 1 " c")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "LINE")
          (cons 100 "AcDbEntity")
          (cons 67 0)
          (cons 8 "0")
          (cons 62 3)
          (cons 100 "AcDbLine")
          (list 10 7.00000000 -39.66200000 0.00000000)
          (list 11 0.00000000 -39.66200000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -42.49500000 0.00000000)
          (list 11 0.00000000 -42.49500000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -25.49700000 0.00000000)
          (list 11 0.00000000 -25.49700000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -28.33000000 0.00000000)
          (list 11 0.00000000 -28.33000000 0.00000000)
          (list 210 0.00000000 0.00000000 1.00000000)
         )
         (list
          (cons 0 "LINE")
          (cons 100 "AcDbEntity")
          (cons 67 0)
          (cons 8 "0")
          (cons 100 "AcDbLine")
          (list 10 1.96719380 -29.77114901 0.00000000)
          (list 11 2.79195186 -29.77114901 0.00000000)
          (list 210 0.00000000 0.00000000 1.00000000)
         )
         (list
          (cons 0 "LINE")
          (cons 100 "AcDbEntity")
          (cons 67 0)
          (cons 8 "0")
          (cons 100 "AcDbLine")
          (list 10 1.96719380 -35.43714901 0.00000000)
          (list 11 2.79195186 -35.43714901 0.00000000)
          (list 210 0.00000000 0.00000000 1.00000000)
         )
         (list
          (cons 0 "TEXT")
          (cons 100 "AcDbEntity")
          (cons 67 0)
          (cons 8 "0")
          (cons 100 "AcDbText")
          (list 10 1.78007918 -4.87450000 0.00000000)
          (cons 40  1.25000000)
          (cons 1 "R")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -24.70750000 0.00000000)
          (cons 40  1.25000000)
          (cons 1 "e")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -13.37450000 0.00000000)
          (cons 40  1.25000000)
          (cons 1 "A.D.1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -19.04083333 0.00000000)
          (cons 40  1.25000000)
          (cons 1 "ARC")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -21.87416667 0.00000000)
          (cons 40  1.25000000)
          (cons 1 "Ext")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -30.37416667 0.00000000)
          (cons 40  1.25000000)
          (cons 1 "0s1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -27.54083333 0.00000000)
          (cons 40  1.25000000)
          (cons 1 "Ls1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -33.20683333 0.00000000)
          (cons 40  1.25000000)
          (cons 1 "Ls2")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -36.04016667 0.00000000)
          (cons 40  1.25000000)
          (cons 1 "0s2")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -38.87350000 0.00000000)
          (cons 40  1.25000000)
          (cons 1 "PI")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -44.54016667 0.00000000)
          (cons 40  1.25000000)
          (cons 1 "E.")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -41.70683333 0.00000000)
          (cons 40  1.25000000)
          (cons 1 "N.")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "LINE")
          (cons 100 "AcDbEntity")
          (cons 67 0)
          (cons 8 "0")
          (cons 62 30)
          (cons 100 "AcDbLine")
          (list 10 7.00000000 -14.16500000 0.00000000)
          (list 11 0.00000000 -14.16500000 0.00000000)
          (list 210 0.00000000 0.00000000 1.00000000)
         )
         (list
          (cons 0 "TEXT")
          (cons 100 "AcDbEntity")
          (cons 67 0)
          (cons 8 "0")
          (cons 100 "AcDbText")
          (list 10 1.78007917 -16.20750000 0.00000000)
          (cons 40  1.25000000)
          (cons 1 "A.D.2")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "ATTDEF")
          (cons 100 "AcDbEntity")
          (cons 67 0)
          (cons 8 "0")
          (cons 62 2)
          (cons 100 "AcDbText")
          (list 10 -2.59047618 -44.52800000 0.00000000)
          (cons 40  0.80000000)
          (cons 1 "7.0")
          (cons 50  0.00000000)
          (cons 41  1.00000000)
          (cons 51  0.00000000)
          (cons 7 "Standard")
          (cons 71 0)
          (cons 72 2)
          (list 11 -0.79999999 -44.52800000 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list (cons 0 "ENDBLK"))
        )
       )
       ((= (strcase BLKNAME) "BCCURVETABLEDATA")
        (list
         (list
          (cons 0 "BLOCK")
          (cons 2 "BCCurveTableData")
          (cons 70  2)
          (list 10 0.00000000 0.00000000 0.00000000)
         )
         (list
          (cons 0 "LINE")
          (cons 100 "AcDbEntity")
          (cons 67 0)
          (cons 8 "0")
          (cons 62 3)
          (cons 100 "AcDbLine")
          (list 10 20.00000000 0.00000000 0.00000000)
          (list 11 0.00000000 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 -45.32799986 0.00000000)
          (list 11 20.00000000 -45.32799944 0.00000000)
          (list 210 0.00000000 0.00000000 1.00000000)
         )
         (list
          (cons 0 "LINE")
          (cons 100 "AcDbEntity")
          (cons 67 0)
          (cons 8 "0")
          (cons 62 3)
          (cons 100 "AcDbLine")
          (list 10 20.00000000 -2.83300000 0.00000000)
          (list 11 0.00000000 -2.83300000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -5.66600000 0.00000000)
          (list 11 0.00000000 -5.66600000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -8.49900000 0.00000000)
          (list 11 0.00000000 -8.49900000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -11.33200000 0.00000000)
          (list 11 0.00000000 -11.33200000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -14.16500000 0.00000000)
          (list 11 0.00000000 -14.16500000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -16.99800000 0.00000000)
          (list 11 0.00000000 -16.99800000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -19.83100000 0.00000000)
          (list 11 0.00000000 -19.83100000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -28.33000000 0.00000000)
          (list 11 0.00000000 -28.33000000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -31.16300000 0.00000000)
          (list 11 0.00000000 -31.16300000 0.00000000)
          (list 210 0.00000000 0.00000000 1.00000000)
         )
         (list
          (cons 0 "LINE")
          (cons 100 "AcDbEntity")
          (cons 67 0)
          (cons 8 "0")
          (cons 62 3)
          (cons 100 "AcDbLine")
          (list 10 20.00000000 -36.82900000 0.00000000)
          (list 11 0.00000000 -36.82900000 0.00000000)
          (list 210 0.00000000 0.00000000 1.00000000)
         )
         (list
          (cons 0 "LINE")
          (cons 100 "AcDbEntity")
          (cons 67 0)
          (cons 8 "0")
          (cons 62 3)
          (cons 100 "AcDbLine")
          (list 10 20.00000000 -39.66200000 0.00000000)
          (list 11 0.00000000 -39.66200000 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 0.00000000 0.00000000)
          (list 11 0.00000000 -45.32800000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -22.66400000 0.00000000)
          (list 11 0.00000000 -22.66400000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -25.49700000 0.00000000)
          (list 11 0.00000000 -25.49700000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -33.99600000 0.00000000)
          (list 11 0.00000000 -33.99600000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -42.49500000 0.00000000)
          (list 11 0.00000000 -42.49500000 0.00000000)
          (list 210 0.00000000 0.00000000 1.00000000)
         )
         (list
          (cons 0 "ATTDEF")
          (cons 100 "AcDbEntity")
          (cons 67 0)
          (cons 8 "0")
          (cons 100 "AcDbText")
          (list 10 1.83394390 -2.30830557 0.00000000)
          (cons 40  1.72500000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Number")
          (cons 2 "LABEL")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -4.87449879 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Radius")
          (cons 2 "CRADIUS")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -7.70783213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Total Delta")
          (cons 2 "DELTA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -10.54083213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Delta")
          (cons 2 "CDELTA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -13.37449879 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Tangent In")
          (cons 2 "CTANGENT1")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -16.20749879 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Tangent Out")
          (cons 2 "CTANGENT2")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -19.04083213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Length")
          (cons 2 "CLENGTH")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -21.87383213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "External Distance (Es or Ec)")
          (cons 2 "EXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -24.70683213 0.00000000)
          (cons 40  1.25000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Superelevation")
          (cons 2 "E")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -27.53983213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Length In")
          (cons 2 "LS1")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -30.37283213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Theta In")
          (cons 2 "THETA1")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -33.20583213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Length Out")
          (cons 2 "LS2")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -36.03883213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Theta Out")
          (cons 2 "THETA2")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -38.87183213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "PI Station")
          (cons 2 "PISTA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -41.70483213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "PI Northing")
          (cons 2 "PINORTHING")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -44.53783213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "PI EASTING")
          (cons 2 "PIEASTING")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 -3.35238094 -44.52799986 0.00000000)
          (cons 40  0.80000000)
          (cons 1 "20.0")
          (cons 50  0.00000000)
          (cons 41  1.00000000)
          (cons 51  0.00000000)
          (cons 7 "Standard")
          (cons 71 0)
          (cons 72 2)
          (list 11 -0.79999999 -44.52799986 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list (cons 0 "ENDBLK"))
        )
       )
       ((= (strcase BLKNAME) "CIRC")
        (list
         (list
          (cons 0 "BLOCK")
          (cons 2 "CIRC")
          (cons 70  0)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  5.00000000)
          (list 210 0.00000000 0.00000000 1.00000000)
         )
         (list (cons 0 "ENDBLK"))
        )
       )
       ((= (strcase BLKNAME) "CURVETABLE")
        (list
         (list
          (cons 0 "BLOCK")
          (cons 2 "curvetable")
          (cons 70  2)
          (list 10 0.00000000 0.00000000 0.00000000)
         )
         (list
          (cons 0 "LINE")
          (cons 100 "AcDbEntity")
          (cons 67 0)
          (cons 8 "0")
          (cons 62 3)
          (cons 100 "AcDbLine")
          (list 10 0.00000000 0.00000000 0.00000000)
          (list 11 15.80000000 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 -58.49029637 0.00000000)
          (list 11 0.00000000 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 15.80000000 -58.49029637 0.00000000)
          (list 11 -0.00000001 -58.49029637 0.00000000)
          (list 210 0.00000000 0.00000000 1.00000000)
         )
         (list
          (cons 0 "TEXT")
          (cons 100 "AcDbEntity")
          (cons 67 0)
          (cons 8 "0")
          (cons 62 1)
          (cons 100 "AcDbText")
          (list 10 7.10473687 -52.43607287 0.00000000)
          (cons 40  2.00000000)
          (cons 1 "0")
          (cons 50  0.00000000)
          (cons 41  0.90000000)
          (cons 51  0.00000000)
          (cons 7 "Standard")
          (cons 71 0)
          (cons 72 4)
          (list 11 7.96187973 -51.43607287 0.00000000)
          (list 210 0.00000000 0.00000000 1.00000000)
          (cons 100 "AcDbText")
          (cons 73 0)
         )
         (list
          (cons 0 "LINE")
          (cons 100 "AcDbEntity")
          (cons 67 0)
          (cons 8 "0")
          (cons 62 1)
          (cons 100 "AcDbLine")
          (list 10 6.73510857 -51.43607287 0.00000000)
          (list 11 9.18865088 -51.43607287 0.00000000)
          (list 210 0.00000000 0.00000000 1.00000000)
         )
         (list
          (cons 0 "LINE")
          (cons 100 "AcDbEntity")
          (cons 67 0)
          (cons 8 "0")
          (cons 62 1)
          (cons 100 "AcDbLine")
          (list 10 6.73510857 -35.30000578 0.00000000)
          (list 11 9.18865088 -35.30000578 0.00000000)
          (list 210 0.00000000 0.00000000 1.00000000)
         )
         (list
          (cons 0 "TEXT")
          (cons 100 "AcDbEntity")
          (cons 67 0)
          (cons 8 "0")
          (cons 62 2)
          (cons 100 "AcDbText")
          (list 10 2.71616545 -5.06100582 0.00000000)
          (cons 40  2.40000000)
          (cons 1 "CURVE")
          (cons 50  0.00000000)
          (cons 41  0.90000000)
          (cons 51  0.00000000)
          (cons 7 "Standard")
          (cons 71 0)
          (cons 72 4)
          (list 11 7.96187974 -3.86100582 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 7.10473687 -36.30000578 0.00000000)
          (cons 40  2.00000000)
          (cons 1 "0")
          (cons 50  0.00000000)
          (cons 41  0.90000000)
          (cons 51  0.00000000)
          (cons 7 "Standard")
          (cons 71 0)
          (cons 72 4)
          (list 11 7.96187973 -35.30000578 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 6.59045117 -24.09649276 0.00000000)
          (cons 40  2.00000000)
          (cons 1 "Tc")
          (cons 50  0.00000000)
          (cons 41  0.90000000)
          (cons 51  0.00000000)
          (cons 7 "Standard")
          (cons 71 0)
          (cons 72 4)
          (list 11 7.96187974 -23.09649276 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 7.01902260 -16.09649277 0.00000000)
          (cons 40  2.00000000)
          (cons 1 "R")
          (cons 50  0.00000000)
          (cons 41  0.90000000)
          (cons 51  0.00000000)
          (cons 7 "Standard")
          (cons 71 0)
          (cons 72 4)
          (list 11 7.96187974 -15.09649277 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 6.46187973 -56.43607287 0.00000000)
          (cons 40  2.00000000)
          (cons 1 "Ls")
          (cons 50  0.00000000)
          (cons 41  0.90000000)
          (cons 51  0.00000000)
          (cons 7 "Standard")
          (cons 71 0)
          (cons 72 4)
          (list 11 7.96187973 -55.43607287 0.00000000)
          (list 210 0.00000000 0.00000000 1.00000000)
          (cons 100 "AcDbText")
          (cons 73 0)
         )
         (list
          (cons 0 "LWPOLYLINE")
          (cons 100 "AcDbEntity")
          (cons 67 0)
          (cons 8 "0")
          (cons 62 1)
          (cons 100 "AcDbPolyline")
          (cons 90 3)
          (cons 70 129)
          (cons 43  0.00000000)
          (cons 38  0.00000000)
          (cons 39  0.00000000)
          (list 10 7.56274961 -10.31684399)
          (cons 40  0.00000000)
          (cons 41  0.00000000)
          (cons 42  0.00000000)
          (cons 91 0)
          (list 10 6.76395409 -12.10003338)
          (cons 40  0.00000000)
          (cons 41  0.00000000)
          (cons 42  0.00000000)
          (cons 91 0)
          (list 10 8.36154514 -12.10003338)
          (cons 40  0.00000000)
          (cons 41  0.00000000)
          (cons 42  0.00000000)
          (cons 91 0)
          (list 210 0.00000000 0.00000000 1.00000000)
         )
         (list
          (cons 0 "TEXT")
          (cons 100 "AcDbEntity")
          (cons 67 0)
          (cons 8 "0")
          (cons 62 1)
          (cons 100 "AcDbText")
          (list 10 6.46187973 -40.30000578 0.00000000)
          (cons 40  2.00000000)
          (cons 1 "Ls")
          (cons 50  0.00000000)
          (cons 41  0.90000000)
          (cons 51  0.00000000)
          (cons 7 "Standard")
          (cons 71 0)
          (cons 72 4)
          (list 11 7.96187973 -39.30000578 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 6.41902260 -20.09649276 0.00000000)
          (cons 40  2.00000000)
          (cons 1 "Lc")
          (cons 50  0.00000000)
          (cons 41  0.90000000)
          (cons 51  0.00000000)
          (cons 7 "Standard")
          (cons 71 0)
          (cons 72 4)
          (list 11 7.96187974 -19.09649276 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 8.36683460 -12.12014532 0.00000000)
          (cons 40  2.00000000)
          (cons 1 "c")
          (cons 50  0.00000000)
          (cons 41  0.90000000)
          (cons 51  0.00000000)
          (cons 7 "Standard")
          (cons 71 0)
          (cons 72 4)
          (list 11 9.13826317 -11.45347865 0.00000000)
          (list 210 0.00000000 0.00000000 1.00000000)
          (cons 100 "AcDbText")
          (cons 73 0)
         )
         (list
          (cons 0 "ATTDEF")
          (cons 100 "AcDbEntity")
          (cons 67 0)
          (cons 8 "0")
          (cons 62 2)
          (cons 100 "AcDbText")
          (list 10 -3.09714286 -57.69029637 0.00000000)
          (cons 40  0.80000000)
          (cons 1 "15.8")
          (cons 50  0.00000000)
          (cons 41  0.90000000)
          (cons 51  0.00000000)
          (cons 7 "Standard")
          (cons 71 0)
          (cons 72 2)
          (list 11 -0.80000000 -57.69029637 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 1)
          (cons 100 "AcDbLine")
          (list 10 15.91670335 -48.54374872 0.00000000)
          (list 11 0.11670335 -48.54374872 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.79999999 -42.35422927 0.00000000)
          (list 11 -0.00000001 -42.35422928 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.91670335 -32.40768164 0.00000000)
          (list 11 0.11670335 -32.40768164 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.91670335 -26.21816219 0.00000000)
          (list 11 0.11670335 -26.21816219 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.80000000 -7.72201164 0.00000000)
          (list 11 0.00000000 -7.72201164 0.00000000)
          (list 210 0.00000000 0.00000000 1.00000000)
         )
         (list (cons 0 "ENDBLK"))
        )
       )
       ((= (strcase BLKNAME) "CURVETABLEDATA")
        (list
         (list
          (cons 0 "BLOCK")
          (cons 2 "curvetableDATA")
          (cons 70  2)
          (list 10 0.00000000 0.00000000 0.00000000)
         )
         (list
          (cons 0 "ATTDEF")
          (cons 100 "AcDbEntity")
          (cons 67 0)
          (cons 8 "0")
          (cons 62 2)
          (cons 100 "AcDbText")
          (list 10 11.90000000 -3.86100582 0.00000000)
          (cons 40  2.40000000)
          (cons 1 "")
          (cons 50  0.00000000)
          (cons 41  0.90000000)
          (cons 51  0.00000000)
          (cons 7 "Standard")
          (cons 71 0)
          (cons 72 4)
          (list 11 11.90000000 -3.86100582 0.00000000)
          (list 210 0.00000000 0.00000000 1.00000000)
          (cons 100 "AcDbAttributeDefinition")
          (cons 280 0)
          (cons 3 "Curve Label")
          (cons 2 "LABEL")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -11.09649276 0.00000000)
          (cons 40  2.00000000)
          (cons 1 "")
          (cons 50  0.00000000)
          (cons 41  0.90000000)
          (cons 51  0.00000000)
          (cons 7 "Standard")
          (cons 71 0)
          (cons 72 4)
          (list 11 11.90000000 -11.09649276 0.00000000)
          (list 210 0.00000000 0.00000000 1.00000000)
          (cons 100 "AcDbAttributeDefinition")
          (cons 280 0)
          (cons 3 "Curve Delta")
          (cons 2 "CDELTA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -15.09649276 0.00000000)
          (cons 40  2.00000000)
          (cons 1 "")
          (cons 50  0.00000000)
          (cons 41  0.90000000)
          (cons 51  0.00000000)
          (cons 7 "Standard")
          (cons 71 0)
          (cons 72 4)
          (list 11 11.90000000 -15.09649276 0.00000000)
          (list 210 0.00000000 0.00000000 1.00000000)
          (cons 100 "AcDbAttributeDefinition")
          (cons 280 0)
          (cons 3 "Curve Radius")
          (cons 2 "CRADIUS")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -19.09649276 0.00000000)
          (cons 40  2.00000000)
          (cons 1 "")
          (cons 50  0.00000000)
          (cons 41  0.90000000)
          (cons 51  0.00000000)
          (cons 7 "Standard")
          (cons 71 0)
          (cons 72 4)
          (list 11 11.90000000 -19.09649276 0.00000000)
          (list 210 0.00000000 0.00000000 1.00000000)
          (cons 100 "AcDbAttributeDefinition")
          (cons 280 0)
          (cons 3 "Curve Length")
          (cons 2 "CLENGTH")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -23.09649275 0.00000000)
          (cons 40  2.00000000)
          (cons 1 "")
          (cons 50  0.00000000)
          (cons 41  0.90000000)
          (cons 51  0.00000000)
          (cons 7 "Standard")
          (cons 71 0)
          (cons 72 4)
          (list 11 11.90000000 -23.09649275 0.00000000)
          (list 210 0.00000000 0.00000000 1.00000000)
          (cons 100 "AcDbAttributeDefinition")
          (cons 280 0)
          (cons 3 "Curve Tangent")
          (cons 2 "CTANGENT")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 11.89999999 -29.39285760 0.00000000)
          (cons 40  2.40000000)
          (cons 1 "")
          (cons 50  0.00000000)
          (cons 41  0.90000000)
          (cons 51  0.00000000)
          (cons 7 "Standard")
          (cons 71 0)
          (cons 72 4)
          (list 11 11.89999999 -29.39285760 0.00000000)
          (list 210 0.00000000 0.00000000 1.00000000)
          (cons 100 "AcDbAttributeDefinition")
          (cons 280 0)
          (cons 3 "Spiral Back Label")
          (cons 2 "SB")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -35.30000578 0.00000000)
          (cons 40  2.00000000)
          (cons 1 "")
          (cons 50  0.00000000)
          (cons 41  0.90000000)
          (cons 51  0.00000000)
          (cons 7 "Standard")
          (cons 71 0)
          (cons 72 4)
          (list 11 11.89999999 -35.30000578 0.00000000)
          (list 210 0.00000000 0.00000000 1.00000000)
          (cons 100 "AcDbAttributeDefinition")
          (cons 280 0)
          (cons 3 "Spiral Back Theta")
          (cons 2 "SBTHETA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -39.30000577 0.00000000)
          (cons 40  2.00000000)
          (cons 1 "")
          (cons 50  0.00000000)
          (cons 41  0.90000000)
          (cons 51  0.00000000)
          (cons 7 "Standard")
          (cons 71 0)
          (cons 72 4)
          (list 11 11.89999999 -39.30000577 0.00000000)
          (list 210 0.00000000 0.00000000 1.00000000)
          (cons 100 "AcDbAttributeDefinition")
          (cons 280 0)
          (cons 3 "Spiral Back Length")
          (cons 2 "SBLENGTH")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 11.89999999 -45.52892469 0.00000000)
          (cons 40  2.40000000)
          (cons 1 "")
          (cons 50  0.00000000)
          (cons 41  0.90000000)
          (cons 51  0.00000000)
          (cons 7 "Standard")
          (cons 71 0)
          (cons 72 4)
          (list 11 11.89999999 -45.52892469 0.00000000)
          (list 210 0.00000000 0.00000000 1.00000000)
          (cons 100 "AcDbAttributeDefinition")
          (cons 280 0)
          (cons 3 "Spiral Ahead Label")
          (cons 2 "SA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -51.43607287 0.00000000)
          (cons 40  2.00000000)
          (cons 1 "")
          (cons 50  0.00000000)
          (cons 41  0.90000000)
          (cons 51  0.00000000)
          (cons 7 "Standard")
          (cons 71 0)
          (cons 72 4)
          (list 11 11.89999999 -51.43607287 0.00000000)
          (list 210 0.00000000 0.00000000 1.00000000)
          (cons 100 "AcDbAttributeDefinition")
          (cons 280 0)
          (cons 3 "Spiral Ahead Theta")
          (cons 2 "SATHETA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -55.43607286 0.00000000)
          (cons 40  2.00000000)
          (cons 1 "")
          (cons 50  0.00000000)
          (cons 41  0.90000000)
          (cons 51  0.00000000)
          (cons 7 "Standard")
          (cons 71 0)
          (cons 72 4)
          (list 11 11.89999999 -55.43607286 0.00000000)
          (list 210 0.00000000 0.00000000 1.00000000)
          (cons 100 "AcDbAttributeDefinition")
          (cons 280 0)
          (cons 3 "Spiral Ahead Length")
          (cons 2 "SALENGTH")
          (cons 70 0)
          (cons 73 0)
          (cons 74 0)
          (cons 280 0)
         )
         (list
          (cons 0 "LINE")
          (cons 100 "AcDbEntity")
          (cons 67 0)
          (cons 8 "0")
          (cons 62 1)
          (cons 100 "AcDbLine")
          (list 10 0.00000000 -32.40768166 0.00000000)
          (list 11 23.80000000 -32.40768168 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -26.21816219 0.00000000)
          (list 11 23.80000000 -26.21816218 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -7.72201164 0.00000000)
          (list 11 23.80000000 -7.72201163 0.00000000)
          (list 210 0.00000000 0.00000000 1.00000000)
         )
         (list
          (cons 0 "LINE")
          (cons 100 "AcDbEntity")
          (cons 67 0)
          (cons 8 "0")
          (cons 62 1)
          (cons 100 "AcDbLine")
          (list 10 23.80000000 -42.35422928 0.00000000)
          (list 11 0.00000000 -42.35422928 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -48.54374875 0.00000000)
          (list 11 23.80000000 -48.54374876 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -58.49029637 0.00000000)
          (list 11 0.00000000 0.00000000 0.00000000)
          (list 210 0.00000000 0.00000000 1.00000000)
         )
         (list
          (cons 0 "ATTDEF")
          (cons 100 "AcDbEntity")
          (cons 67 0)
          (cons 8 "0")
          (cons 62 2)
          (cons 100 "AcDbText")
          (list 10 -3.09714286 -57.69029637 0.00000000)
          (cons 40  0.80000000)
          (cons 1 "23.8")
          (cons 50  0.00000000)
          (cons 41  0.90000000)
          (cons 51  0.00000000)
          (cons 7 "Standard")
          (cons 71 0)
          (cons 72 2)
          (list 11 -0.80000000 -57.69029637 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 3)
          (cons 100 "AcDbLine")
          (list 10 0.00000000 -58.49029637 0.00000000)
          (list 11 23.80000000 -58.49029639 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 0.00000000 0.00000000)
          (list 11 23.80000000 0.00000001 0.00000000)
          (list 210 0.00000000 0.00000000 1.00000000)
         )
         (list (cons 0 "ENDBLK"))
        )
       )
       ((= (strcase BLKNAME) "DRAWGRIDDEF")
        (list
         (list
          (cons 0 "BLOCK")
          (cons 2 "DrawGridDef")
          (cons 70  2)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  1.00000000)
          (list 210 0.00000000 0.00000000 1.00000000)
         )
         (list
          (cons 0 "TEXT")
          (cons 100 "AcDbEntity")
          (cons 67 0)
          (cons 8 "0")
          (cons 100 "AcDbText")
          (list 10 -2.35714286 -1.50000000 0.00000000)
          (cons 40  0.25000000)
          (cons 1 "Title Text : ")
          (cons 50  0.00000000)
          (cons 41  1.00000000)
          (cons 51  0.00000000)
          (cons 7 "Standard")
          (cons 71 0)
          (cons 72 2)
          (list 11 0.00000000 -1.50000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.77380952 -1.90476190 0.00000000)
          (cons 40  0.25000000)
          (cons 1 "Title Text Height : ")
          (cons 50  0.00000000)
          (cons 41  1.00000000)
          (cons 51  0.00000000)
          (cons 7 "Standard")
          (cons 71 0)
          (cons 72 2)
          (list 11 0.00000000 -1.90476190 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.71428571 -2.30952381 0.00000000)
          (cons 40  0.25000000)
          (cons 1 "Title Text Offset : ")
          (cons 50  0.00000000)
          (cons 41  1.00000000)
          (cons 51  0.00000000)
          (cons 7 "Standard")
          (cons 71 0)
          (cons 72 2)
          (list 11 0.00000000 -2.30952381 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.42857143 -2.71428571 0.00000000)
          (cons 40  0.25000000)
          (cons 1 "Base Point 'X' : ")
          (cons 50  0.00000000)
          (cons 41  1.00000000)
          (cons 51  0.00000000)
          (cons 7 "Standard")
          (cons 71 0)
          (cons 72 2)
          (list 11 0.00000000 -2.71428571 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.40476190 -3.11904762 0.00000000)
          (cons 40  0.25000000)
          (cons 1 "Base Point 'Y' : ")
          (cons 50  0.00000000)
          (cons 41  1.00000000)
          (cons 51  0.00000000)
          (cons 7 "Standard")
          (cons 71 0)
          (cons 72 2)
          (list 11 0.00000000 -3.11904762 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.57142857 -3.52380952 0.00000000)
          (cons 40  0.25000000)
          (cons 1 "Grid Width : ")
          (cons 50  0.00000000)
          (cons 41  1.00000000)
          (cons 51  0.00000000)
          (cons 7 "Standard")
          (cons 71 0)
          (cons 72 2)
          (list 11 0.00000000 -3.52380952 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.76190476 -3.92857143 0.00000000)
          (cons 40  0.25000000)
          (cons 1 "Grid Height : ")
          (cons 50  0.00000000)
          (cons 41  1.00000000)
          (cons 51  0.00000000)
          (cons 7 "Standard")
          (cons 71 0)
          (cons 72 2)
          (list 11 0.00000000 -3.92857143 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -4.39285714 -4.33333333 0.00000000)
          (cons 40  0.25000000)
          (cons 1 "Vertical Exageration : ")
          (cons 50  0.00000000)
          (cons 41  1.00000000)
          (cons 51  0.00000000)
          (cons 7 "Standard")
          (cons 71 0)
          (cons 72 2)
          (list 11 0.00000000 -4.33333333 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.78571429 -4.73809524 0.00000000)
          (cons 40  0.25000000)
          (cons 1 "Text Height : ")
          (cons 50  0.00000000)
          (cons 41  1.00000000)
          (cons 51  0.00000000)
          (cons 7 "Standard")
          (cons 71 0)
          (cons 72 2)
          (list 11 0.00000000 -4.73809524 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.72619048 -5.14285714 0.00000000)
          (cons 40  0.25000000)
          (cons 1 "Text Offset : ")
          (cons 50  0.00000000)
          (cons 41  1.00000000)
          (cons 51  0.00000000)
          (cons 7 "Standard")
          (cons 71 0)
          (cons 72 2)
          (list 11 0.00000000 -5.14285714 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -5.15476190 -5.54761905 0.00000000)
          (cons 40  0.25000000)
          (cons 1 "Horizontal Grid Spacing : ")
          (cons 50  0.00000000)
          (cons 41  1.00000000)
          (cons 51  0.00000000)
          (cons 7 "Standard")
          (cons 71 0)
          (cons 72 2)
          (list 11 0.00000000 -5.54761905 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -6.15476190 -5.95238095 0.00000000)
          (cons 40  0.25000000)
          (cons 1 "Horizontal Fine Grid Spacing : ")
          (cons 50  0.00000000)
          (cons 41  1.00000000)
          (cons 51  0.00000000)
          (cons 7 "Standard")
          (cons 71 0)
          (cons 72 2)
          (list 11 0.00000000 -5.95238095 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -6.15476190 -6.35714286 0.00000000)
          (cons 40  0.25000000)
          (cons 1 "Horizontal Grid Text Spacing : ")
          (cons 50  0.00000000)
          (cons 41  1.00000000)
          (cons 51  0.00000000)
          (cons 7 "Standard")
          (cons 71 0)
          (cons 72 2)
          (list 11 0.00000000 -6.35714286 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -4.65476190 -6.76190476 0.00000000)
          (cons 40  0.25000000)
          (cons 1 "Vertical Grid Spacing : ")
          (cons 50  0.00000000)
          (cons 41  1.00000000)
          (cons 51  0.00000000)
          (cons 7 "Standard")
          (cons 71 0)
          (cons 72 2)
          (list 11 0.00000000 -6.76190476 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -5.65476190 -7.16666667 0.00000000)
          (cons 40  0.25000000)
          (cons 1 "Vertical Fine Grid Spacing : ")
          (cons 50  0.00000000)
          (cons 41  1.00000000)
          (cons 51  0.00000000)
          (cons 7 "Standard")
          (cons 71 0)
          (cons 72 2)
          (list 11 0.00000000 -7.16666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -5.65476190 -7.57142857 0.00000000)
          (cons 40  0.25000000)
          (cons 1 "Vertical Grid Text Spacing : ")
          (cons 50  0.00000000)
          (cons 41  1.00000000)
          (cons 51  0.00000000)
          (cons 7 "Standard")
          (cons 71 0)
          (cons 72 2)
          (list 11 0.00000000 -7.57142857 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.58333333 -7.97619048 0.00000000)
          (cons 40  0.25000000)
          (cons 1 "Grid Layer : ")
          (cons 50  0.00000000)
          (cons 41  1.00000000)
          (cons 51  0.00000000)
          (cons 7 "Standard")
          (cons 71 0)
          (cons 72 2)
          (list 11 0.00000000 -7.97619048 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.58333333 -8.38095238 0.00000000)
          (cons 40  0.25000000)
          (cons 1 "Fine Grid Layer : ")
          (cons 50  0.00000000)
          (cons 41  1.00000000)
          (cons 51  0.00000000)
          (cons 7 "Standard")
          (cons 71 0)
          (cons 72 2)
          (list 11 0.00000000 -8.38095238 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.60714286 -8.78571429 0.00000000)
          (cons 40  0.25000000)
          (cons 1 "Text Layer : ")
          (cons 50  0.00000000)
          (cons 41  1.00000000)
          (cons 51  0.00000000)
          (cons 7 "Standard")
          (cons 71 0)
          (cons 72 2)
          (list 11 0.00000000 -8.78571429 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -8.25000000 -9.19047619 0.00000000)
          (cons 40  0.25000000)
          (cons 1 "Station Text Label Flag (1 = Use '+') : ")
          (cons 50  0.00000000)
          (cons 41  1.00000000)
          (cons 51  0.00000000)
          (cons 7 "Standard")
          (cons 71 0)
          (cons 72 2)
          (list 11 0.00000000 -9.19047619 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.08333333 -9.59523810 0.00000000)
          (cons 40  0.25000000)
          (cons 1 "Master Scale : ")
          (cons 50  0.00000000)
          (cons 41  1.00000000)
          (cons 51  0.00000000)
          (cons 7 "Standard")
          (cons 71 0)
          (cons 72 2)
          (list 11 0.00000000 -9.59523810 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -10.61904762 -10.00000001 0.00000000)
          (cons 40  0.25000000)
          (cons 1 "Direction (1 = Left to Right, -1 = Right to Left) : ")
          (cons 50  0.00000000)
          (cons 41  1.00000000)
          (cons 51  0.00000000)
          (cons 7 "Standard")
          (cons 71 0)
          (cons 72 2)
          (list 11 0.00000000 -10.00000001 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 0.00000000 -1.50000000 0.00000000)
          (cons 40  0.25000000)
          (cons 1 "Grid Title")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Title Text")
          (cons 2 "TITLE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -1.90476190 0.00000000)
          (cons 40  0.25000000)
          (cons 1 "5.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Title Text Height")
          (cons 2 "TITLEHEIGHT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -2.30952381 0.00000000)
          (cons 40  0.25000000)
          (cons 1 "5.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Title Text Offset")
          (cons 2 "TITLEOFFSET")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -2.71428571 0.00000000)
          (cons 40  0.25000000)
          (cons 1 "0.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Base Point 'X'")
          (cons 2 "BX")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -3.11904762 0.00000000)
          (cons 40  0.25000000)
          (cons 1 "0.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Base Point 'Y'")
          (cons 2 "BY")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -3.52380952 0.00000000)
          (cons 40  0.25000000)
          (cons 1 "500.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Grid Width")
          (cons 2 "W")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -3.92857143 0.00000000)
          (cons 40  0.25000000)
          (cons 1 "200.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Grid Height")
          (cons 2 "H")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -4.33333333 0.00000000)
          (cons 40  0.25000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Exageration")
          (cons 2 "VEXAG")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -4.73809524 0.00000000)
          (cons 40  0.25000000)
          (cons 1 "2.5")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Height")
          (cons 2 "THEIGHT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -5.14285714 0.00000000)
          (cons 40  0.25000000)
          (cons 1 "2.5")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Offset")
          (cons 2 "TOFFSET")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -5.54761905 0.00000000)
          (cons 40  0.25000000)
          (cons 1 "100.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Horizontal Grid Spacing")
          (cons 2 "HINC")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -5.95238095 0.00000000)
          (cons 40  0.25000000)
          (cons 1 "20.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Horizontal Fine Grid Spacing")
          (cons 2 "HINCFINE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -6.35714286 0.00000000)
          (cons 40  0.25000000)
          (cons 1 "100.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Horizontal Grid Text Spacing")
          (cons 2 "HINCTEXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -6.76190476 0.00000000)
          (cons 40  0.25000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Grid Spacing")
          (cons 2 "VINC")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -7.16666667 0.00000000)
          (cons 40  0.25000000)
          (cons 1 "1.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Fine Grid Spacing")
          (cons 2 "VINCFINE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -7.57142857 0.00000000)
          (cons 40  0.25000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Grid Text Spacing")
          (cons 2 "VINCTEXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -7.97619048 0.00000000)
          (cons 40  0.25000000)
          (cons 1 "PR-GRID")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Grid Layer")
          (cons 2 "LAY")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -8.38095238 0.00000000)
          (cons 40  0.25000000)
          (cons 1 "PR-GRID-MIN")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Fine Grid Layer")
          (cons 2 "LAYFINE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -8.78571429 0.00000000)
          (cons 40  0.25000000)
          (cons 1 "PR-GRID-TXT")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Layer")
          (cons 2 "LAYTEXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -9.19047619 0.00000000)
          (cons 40  0.25000000)
          (cons 1 "0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Station Text Label Flag (1 = Use '+')")
          (cons 2 "TFLAG")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -9.59523810 0.00000000)
          (cons 40  0.25000000)
          (cons 1 "1.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Master Scale")
          (cons 2 "MASTER")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -10.00000001 0.00000000)
          (cons 40  0.25000000)
          (cons 1 "1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Direction")
          (cons 2 "DIRECTION")
          (cons 70 0)
          (cons 73 0)
          (cons 74 0)
          (cons 280 0)
         )
         (list (cons 0 "ENDBLK"))
        )
       )
       ((= (strcase BLKNAME) "FORCE")
        (list
         (list
          (cons 0 "BLOCK")
          (cons 2 "Force")
          (cons 70  2)
          (list 10 0.00000000 0.00000000 0.00000000)
         )
         (list
          (cons 0 "CIRCLE")
          (cons 100 "AcDbEntity")
          (cons 67 0)
          (cons 8 "0")
          (cons 100 "AcDbCircle")
          (list 10 7.50000000 0.00000000 0.00000000)
          (cons 40  2.50000000)
          (list 210 0.00000000 0.00000000 1.00000000)
         )
         (list
          (cons 0 "SOLID")
          (cons 100 "AcDbEntity")
          (cons 67 0)
          (cons 8 "0")
          (cons 100 "AcDbTrace")
          (list 10 2.50000000 1.00000000 0.00000000)
          (list 11 0.00000000 0.00000000 0.00000000)
          (list 12 2.50000000 -1.00000000 0.00000000)
          (list 13 2.50000000 -1.00000000 0.00000000)
          (cons 39  0.00000000)
          (list 210 0.00000000 0.00000000 1.00000000)
         )
         (list
          (cons 0 "LINE")
          (cons 100 "AcDbEntity")
          (cons 67 0)
          (cons 8 "0")
          (cons 100 "AcDbLine")
          (list 10 2.50000000 0.00000000 0.00000000)
          (list 11 5.00000000 0.00000000 0.00000000)
          (list 210 0.00000000 0.00000000 1.00000000)
         )
         (list
          (cons 0 "ATTDEF")
          (cons 100 "AcDbEntity")
          (cons 67 0)
          (cons 8 "0")
          (cons 100 "AcDbText")
          (list 10 7.50000000 0.00000000 0.00000000)
          (cons 40  1.00000000)
          (cons 1 "")
          (cons 50  4.71238898)
          (cons 41  1.00000000)
          (cons 51  0.00000000)
          (cons 7 "Standard")
          (cons 71 0)
          (cons 72 4)
          (list 11 7.50000000 0.00000000 0.00000000)
          (list 210 0.00000000 0.00000000 1.00000000)
          (cons 100 "AcDbAttributeDefinition")
          (cons 280 0)
          (cons 3 "Force")
          (cons 2 "F")
          (cons 70 0)
          (cons 73 0)
          (cons 74 0)
          (cons 280 0)
         )
         (list (cons 0 "ENDBLK"))
        )
       )
       ((= (strcase BLKNAME) "LKI")
        (list
         (list
          (cons 0 "BLOCK")
          (cons 2 "LKI")
          (cons 70  2)
          (cons 4 "")
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "TEXT")
          (cons 100 "AcDbEntity")
          (cons 67 0)
          (cons 8 "0")
          (cons 100 "AcDbText")
          (list 10 -6.25240055 0.80315501 0.00000000)
          (cons 40  1.00000000)
          (cons 1 "Segment :")
          (cons 50  0.00000000)
          (cons 41  1.00000000)
          (cons 51  0.00000000)
          (cons 7 "Standard")
          (cons 71 0)
          (cons 72 2)
          (list 11 0.00000000 0.50000000 0.00000000)
          (list 210 0.00000000 0.00000000 1.00000000)
          (cons 100 "AcDbText")
          (cons 73 1)
         )
         (list
          (cons 0 "TEXT")
          (cons 100 "AcDbEntity")
          (cons 67 0)
          (cons 8 "0")
          (cons 100 "AcDbText")
          (list 10 -2.82030178 -1.50000000 0.00000000)
          (cons 40  1.00000000)
          (cons 1 "Km :")
          (cons 50  0.00000000)
          (cons 41  1.00000000)
          (cons 51  0.00000000)
          (cons 7 "Standard")
          (cons 71 0)
          (cons 72 2)
          (list 11 0.00000000 -0.50000000 0.00000000)
          (list 210 0.00000000 0.00000000 1.00000000)
          (cons 100 "AcDbText")
          (cons 73 3)
         )
         (list
          (cons 0 "ATTDEF")
          (cons 100 "AcDbEntity")
          (cons 67 0)
          (cons 8 "0")
          (cons 100 "AcDbText")
          (list 10 1.00000000 0.80315501 0.00000000)
          (cons 40  1.00000000)
          (cons 1 "0123")
          (cons 50  0.00000000)
          (cons 41  1.00000000)
          (cons 51  0.00000000)
          (cons 7 "Standard")
          (cons 71 0)
          (cons 72 0)
          (list 11 1.00000000 0.50000000 0.00000000)
          (list 210 0.00000000 0.00000000 1.00000000)
          (cons 100 "AcDbAttributeDefinition")
          (cons 280 0)
          (cons 3 "Segment")
          (cons 2 "SEGMENT")
          (cons 70 0)
          (cons 73 0)
          (cons 74 1)
          (cons 280 1)
         )
         (list
          (cons 0 "ATTDEF")
          (cons 100 "AcDbEntity")
          (cons 67 0)
          (cons 8 "0")
          (cons 100 "AcDbText")
          (list 10 1.00000000 -1.50000000 0.00000000)
          (cons 40  1.00000000)
          (cons 1 "0123")
          (cons 50  0.00000000)
          (cons 41  1.00000000)
          (cons 51  0.00000000)
          (cons 7 "Standard")
          (cons 71 0)
          (cons 72 0)
          (list 11 1.00000000 -0.50000000 0.00000000)
          (list 210 0.00000000 0.00000000 1.00000000)
          (cons 100 "AcDbAttributeDefinition")
          (cons 280 0)
          (cons 3 "Km")
          (cons 2 "KM")
          (cons 70 0)
          (cons 73 0)
          (cons 74 3)
          (cons 280 1)
         )
         (list (cons 0 "ENDBLK"))
        )
       )
       ((= (strcase BLKNAME) "LTESTTRAINSECTION")
        (list
         (list
          (cons 0 "BLOCK")
          (cons 2 "LTESTTRAINSECTION")
          (cons 70  0)
          (cons 4 "")
          (list 10 0.00000000 0.00000000 0.00000000)
         )
         (list
          (cons 0 "LWPOLYLINE")
          (cons 100 "AcDbEntity")
          (cons 67 0)
          (cons 8 "0")
          (cons 6 "DASHED")
          (cons 100 "AcDbPolyline")
          (cons 90 11)
          (cons 70 0)
          (cons 43  0.00000000)
          (cons 38  0.00000000)
          (cons 39  0.00000000)
          (list 10 -0.98500000 0.37264481)
          (cons 40  0.00000000)
          (cons 41  0.00000000)
          (cons 42  0.00000000)
          (cons 91 0)
          (list 10 -1.19260839 0.37264481)
          (cons 40  0.00000000)
          (cons 41  0.00000000)
          (cons 42  -0.36674153)
          (cons 91 0)
          (list 10 -1.38990017 0.53984304)
          (cons 40  0.00000000)
          (cons 41  0.00000000)
          (cons 42  0.00000000)
          (cons 91 0)
          (list 10 -1.53397065 1.40637923)
          (cons 40  0.00000000)
          (cons 41  0.00000000)
          (cons 42  -0.03126153)
          (cons 91 0)
          (list 10 -1.55309759 1.59278654)
          (cons 40  0.00000000)
          (cons 41  0.00000000)
          (cons 42  0.00000000)
          (cons 91 0)
          (list 10 -1.59200204 2.57105401)
          (cons 40  0.00000000)
          (cons 41  0.00000000)
          (cons 42  0.00000000)
          (cons 91 0)
          (list 10 -1.59200204 2.73424074)
          (cons 40  0.00000000)
          (cons 41  0.00000000)
          (cons 42  -0.22029118)
          (cons 91 0)
          (list 10 -1.53903384 2.84862968)
          (cons 40  0.00000000)
          (cons 41  0.00000000)
          (cons 42  0.00000000)
          (cons 91 0)
          (list 10 -1.28083281 3.06765181)
          (cons 40  0.00000000)
          (cons 41  0.00000000)
          (cons 42  -0.17771548)
          (cons 91 0)
          (list 10 -0.12000000 3.49366052)
          (cons 40  0.00000000)
          (cons 41  0.00000000)
          (cons 42  0.00000000)
          (cons 91 0)
          (list 10 0.00000000 3.49366052)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 6 "DASHED2")
          (cons 100 "AcDbLine")
          (list 10 -0.11999839 3.59366052 0.00000000)
          (list 11 0.00000000 3.59366052 0.00000000)
          (list 210 0.00000000 0.00000000 1.00000000)
         )
         (list
          (cons 0 "ARC")
          (cons 100 "AcDbEntity")
          (cons 67 0)
          (cons 8 "0")
          (cons 6 "DASHED2")
          (cons 100 "AcDbCircle")
          (list 10 -1.19260839 0.57264481 0.00000000)
          (cons 40  0.30000000)
          (list 210 0.00000000 0.00000000 1.00000000)
          (cons 100 "AcDbArc")
          (cons 50  3.30634583)
          (cons 51  4.71238898)
         )
         (list
          (cons 0 "ARC")
          (cons 100 "AcDbEntity")
          (cons 67 0)
          (cons 8 "0")
          (cons 6 "DASHED2")
          (cons 100 "AcDbCircle")
          (list 10 -1.44200204 2.73424074 0.00000000)
          (cons 40  0.25000000)
          (list 210 0.00000000 0.00000000 1.00000000)
          (cons 100 "AcDbArc")
          (cons 50  2.27428054)
          (cons 51  3.14159265)
         )
         (list
          (cons 0 "ARC")
          (cons 100 "AcDbEntity")
          (cons 67 0)
          (cons 8 "0")
          (cons 6 "DASHED2")
          (cons 100 "AcDbCircle")
          (list 10 -0.12005876 1.69923732 0.00000000)
          (cons 40  1.89442321)
          (list 210 0.00000000 0.00000000 1.00000000)
          (cons 100 "AcDbArc")
          (cons 50  1.57076446)
          (cons 51  1.74529651)
         )
         (list (cons 0 "ENDBLK"))
        )
       )
       ((= (strcase BLKNAME) "LTRAINSECTION")
        (list
         (list
          (cons 0 "BLOCK")
          (cons 2 "LTRAINSECTION")
          (cons 70  0)
          (cons 4 "")
          (list 10 0.00000000 0.00000000 0.00000000)
         )
         (list
          (cons 0 "LWPOLYLINE")
          (cons 100 "AcDbEntity")
          (cons 67 0)
          (cons 8 "0")
          (cons 6 "DASHED")
          (cons 100 "AcDbPolyline")
          (cons 90 11)
          (cons 70 0)
          (cons 43  0.00000000)
          (cons 38  0.00000000)
          (cons 39  0.00000000)
          (list 10 -0.98500000 0.37264481)
          (cons 40  0.00000000)
          (cons 41  0.00000000)
          (cons 42  0.00000000)
          (cons 91 0)
          (list 10 -1.19260839 0.37264481)
          (cons 40  0.00000000)
          (cons 41  0.00000000)
          (cons 42  -0.36674153)
          (cons 91 0)
          (list 10 -1.38990017 0.53984304)
          (cons 40  0.00000000)
          (cons 41  0.00000000)
          (cons 42  0.00000000)
          (cons 91 0)
          (list 10 -1.53397065 1.40637923)
          (cons 40  0.00000000)
          (cons 41  0.00000000)
          (cons 42  -0.03126153)
          (cons 91 0)
          (list 10 -1.55309759 1.59278654)
          (cons 40  0.00000000)
          (cons 41  0.00000000)
          (cons 42  0.00000000)
          (cons 91 0)
          (list 10 -1.59200204 2.57105401)
          (cons 40  0.00000000)
          (cons 41  0.00000000)
          (cons 42  0.00000000)
          (cons 91 0)
          (list 10 -1.59200204 2.73424074)
          (cons 40  0.00000000)
          (cons 41  0.00000000)
          (cons 42  -0.22029118)
          (cons 91 0)
          (list 10 -1.53903384 2.84862968)
          (cons 40  0.00000000)
          (cons 41  0.00000000)
          (cons 42  0.00000000)
          (cons 91 0)
          (list 10 -1.28083281 3.06765181)
          (cons 40  0.00000000)
          (cons 41  0.00000000)
          (cons 42  -0.17771548)
          (cons 91 0)
          (list 10 -0.12000000 3.49366052)
          (cons 40  0.00000000)
          (cons 41  0.00000000)
          (cons 42  0.00000000)
          (cons 91 0)
          (list 10 0.00000000 3.49366052)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 6 "DASHED2")
          (cons 100 "AcDbLine")
          (list 10 -0.11999839 3.59366052 0.00000000)
          (list 11 0.00000000 3.59366052 0.00000000)
          (list 210 0.00000000 0.00000000 1.00000000)
         )
         (list
          (cons 0 "ARC")
          (cons 100 "AcDbEntity")
          (cons 67 0)
          (cons 8 "0")
          (cons 6 "DASHED2")
          (cons 100 "AcDbCircle")
          (list 10 -1.19260839 0.57264481 0.00000000)
          (cons 40  0.30000000)
          (list 210 0.00000000 0.00000000 1.00000000)
          (cons 100 "AcDbArc")
          (cons 50  3.30634583)
          (cons 51  4.71238898)
         )
         (list
          (cons 0 "ARC")
          (cons 100 "AcDbEntity")
          (cons 67 0)
          (cons 8 "0")
          (cons 6 "DASHED2")
          (cons 100 "AcDbCircle")
          (list 10 -1.44200204 2.73424074 0.00000000)
          (cons 40  0.25000000)
          (list 210 0.00000000 0.00000000 1.00000000)
          (cons 100 "AcDbArc")
          (cons 50  2.27428054)
          (cons 51  3.14159265)
         )
         (list
          (cons 0 "ARC")
          (cons 100 "AcDbEntity")
          (cons 67 0)
          (cons 8 "0")
          (cons 6 "DASHED2")
          (cons 100 "AcDbCircle")
          (list 10 -0.12005876 1.69923732 0.00000000)
          (cons 40  1.89442321)
          (list 210 0.00000000 0.00000000 1.00000000)
          (cons 100 "AcDbArc")
          (cons 50  1.57076446)
          (cons 51  1.74529651)
         )
         (list (cons 0 "ENDBLK"))
        )
       )
       ((= (strcase BLKNAME) "PLACEMARKPOINT")
        (list
         (list
          (cons 0 "BLOCK")
          (cons 2 "PlacemarkPoint")
          (cons 70  2)
          (cons 4 "")
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 102 "{ACAD_XDICTIONARY")
          (cons 102 "}")
          (cons 100 "AcDbEntity")
          (cons 67 0)
          (cons 8 "0")
          (cons 100 "AcDbText")
          (list 10 0.00000000 0.37894376 0.00000000)
          (cons 40  1.25000000)
          (cons 1 "")
          (cons 50  0.00000000)
          (cons 41  1.00000000)
          (cons 51  0.00000000)
          (cons 7 "Standard")
          (cons 71 0)
          (cons 72 1)
          (list 11 0.00000000 0.00000000 0.00000000)
          (list 210 0.00000000 0.00000000 1.00000000)
          (cons 100 "AcDbAttributeDefinition")
          (cons 280 0)
          (cons 3 "Name")
          (cons 2 "NAME")
          (cons 70 0)
          (cons 73 0)
          (cons 74 1)
          (cons 280 1)
         )
         (list (cons 0 "ENDBLK"))
        )
       )
       ((= (strcase BLKNAME) "POINT")
        (list
         (list
          (cons 0 "BLOCK")
          (cons 2 "point")
          (cons 70  2)
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 9.00000000 1.82142857 0.00000000)
          (cons 40  1.50000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Station")
          (cons 2 "STA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 9.00000000 -0.75000000 0.00000000)
          (cons 40  1.50000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Offset")
          (cons 2 "OFFSET")
          (cons 70 0)
          (cons 73 0)
          (cons 74 0)
          (cons 280 0)
         )
         (list
          (cons 0 "ATTDEF")
          (cons 100 "AcDbEntity")
          (cons 67 0)
          (cons 8 "0")
          (cons 100 "AcDbText")
          (list 10 9.00000000 -3.32142857 0.00000000)
          (cons 40  1.50000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Elevation")
          (cons 2 "ELEV")
          (cons 70 0)
          (cons 73 0)
          (cons 74 0)
          (cons 280 0)
         )
         (list
          (cons 0 "TEXT")
          (cons 100 "AcDbEntity")
          (cons 67 0)
          (cons 8 "0")
          (cons 100 "AcDbText")
          (list 10 3.00000000 1.82142857 0.00000000)
          (cons 40  1.50000000)
          (cons 1 "Sta:")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 3.00000000 -0.75000000 0.00000000)
          (cons 40  1.50000000)
          (cons 1 "O/S:")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 3.00000000 -3.32142857 0.00000000)
          (cons 40  1.50000000)
          (cons 1 "Elev:")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list (cons 0 "ENDBLK"))
        )
       )
       ((= (strcase BLKNAME) "PPSLOPE")
        (list
         (list
          (cons 0 "BLOCK")
          (cons 2 "PPSLOPE")
          (cons 70  2)
          (cons 4 "Slope Indicator # (Attribute)")
          (list 10 0.00000000 0.00000000 0.00000000)
         )
         (list
          (cons 0 "SOLID")
          (cons 100 "AcDbEntity")
          (cons 67 0)
          (cons 8 "0")
          (cons 100 "AcDbTrace")
          (list 10 1.50000000 -0.25000000 0.00000000)
          (list 11 2.50000000 0.00000000 0.00000000)
          (list 12 1.50000000 0.25000000 0.00000000)
          (list 13 1.50000000 0.25000000 0.00000000)
          (cons 39  0.00000000)
          (list 210 0.00000000 0.00000000 1.00000000)
         )
         (list
          (cons 0 "LINE")
          (cons 100 "AcDbEntity")
          (cons 67 0)
          (cons 8 "0")
          (cons 100 "AcDbLine")
          (list 10 -2.50000000 0.00000000 0.00000000)
          (list 11 1.50000000 0.00000000 0.00000000)
          (list 210 0.00000000 0.00000000 1.00000000)
         )
         (list
          (cons 0 "ATTDEF")
          (cons 100 "AcDbEntity")
          (cons 67 0)
          (cons 8 "0")
          (cons 100 "AcDbText")
          (list 10 0.00000000 1.20000000 0.00000000)
          (cons 40  0.75000000)
          (cons 1 "")
          (cons 50  0.00000000)
          (cons 41  1.00000000)
          (cons 51  0.00000000)
          (cons 7 "Standard")
          (cons 71 0)
          (cons 72 4)
          (list 11 0.00000000 1.20000000 0.00000000)
          (list 210 0.00000000 0.00000000 1.00000000)
          (cons 100 "AcDbAttributeDefinition")
          (cons 280 0)
          (cons 3 "Slope:")
          (cons 2 "SLOPE")
          (cons 70 0)
          (cons 73 0)
          (cons 74 0)
          (cons 280 0)
         )
         (list (cons 0 "ENDBLK"))
        )
       )
       ((= (strcase BLKNAME) "PR-CIRCLE")
        (list
         (list
          (cons 0 "BLOCK")
          (cons 2 "PR-CIRCLE")
          (cons 70  0)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  5.00000000)
          (list 210 0.00000000 0.00000000 1.00000000)
         )
         (list (cons 0 "ENDBLK"))
        )
       )
       ((= (strcase BLKNAME) "PVI2")
        (list
         (list
          (cons 0 "BLOCK")
          (cons 2 "PVI2")
          (cons 70  2)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  0.01254212)
          (list 210 0.00000000 0.00000000 1.00000000)
         )
         (list
          (cons 0 "LINE")
          (cons 100 "AcDbEntity")
          (cons 67 0)
          (cons 8 "0")
          (cons 100 "AcDbLine")
          (list 10 0.00000000 0.10000000 0.00000000)
          (list 11 -0.07500000 -0.05000000 0.00000000)
          (list 210 0.00000000 0.00000000 1.00000000)
         )
         (list
          (cons 0 "LINE")
          (cons 100 "AcDbEntity")
          (cons 67 0)
          (cons 8 "0")
          (cons 100 "AcDbLine")
          (list 10 0.07500000 -0.05000000 0.00000000)
          (list 11 0.00000000 0.10000000 0.00000000)
          (list 210 0.00000000 0.00000000 1.00000000)
         )
         (list
          (cons 0 "LINE")
          (cons 100 "AcDbEntity")
          (cons 67 0)
          (cons 8 "0")
          (cons 100 "AcDbLine")
          (list 10 -0.07500000 -0.05000000 0.00000000)
          (list 11 0.07500000 -0.05000000 0.00000000)
          (list 210 0.00000000 0.00000000 1.00000000)
         )
         (list
          (cons 0 "ATTDEF")
          (cons 100 "AcDbEntity")
          (cons 67 0)
          (cons 8 "0")
          (cons 100 "AcDbText")
          (list 10 -0.01187849 -0.00514594 0.00000000)
          (cons 40  0.01000000)
          (cons 1 "0.0")
          (cons 50  0.00000000)
          (cons 41  1.00000000)
          (cons 51  0.00000000)
          (cons 7 "Standard")
          (cons 71 0)
          (cons 72 1)
          (list 11 0.00002627 -0.00514594 0.00000000)
          (list 210 0.00000000 0.00000000 1.00000000)
          (cons 100 "AcDbAttributeDefinition")
          (cons 280 0)
          (cons 3 "K")
          (cons 2 "K")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -0.01187849 -0.03250605 0.00000000)
          (cons 40  0.01000000)
          (cons 1 "0.0")
          (cons 50  0.00000000)
          (cons 41  1.00000000)
          (cons 51  0.00000000)
          (cons 7 "Standard")
          (cons 71 0)
          (cons 72 1)
          (list 11 0.00002627 -0.03250605 0.00000000)
          (list 210 0.00000000 0.00000000 1.00000000)
          (cons 100 "AcDbAttributeDefinition")
          (cons 280 0)
          (cons 3 "LENGTH")
          (cons 2 "LENGTH")
          (cons 70 1)
          (cons 73 0)
          (cons 74 0)
          (cons 280 0)
         )
         (list (cons 0 "ENDBLK"))
        )
       )
       ((= (strcase BLKNAME) "RFLALIGN")
        (list
         (list
          (cons 0 "BLOCK")
          (cons 2 "RFLAlign")
          (cons 70  2)
          (list 10 0.00000000 0.00000000 0.00000000)
         )
         (list
          (cons 0 "TEXT")
          (cons 100 "AcDbEntity")
          (cons 67 0)
          (cons 8 "0")
          (cons 100 "AcDbText")
          (list 10 -3.38095238 0.00000000 0.00000000)
          (cons 40  1.00000000)
          (cons 1 "HOR:")
          (cons 50  0.00000000)
          (cons 41  1.00000000)
          (cons 51  0.00000000)
          (cons 7 "Standard")
          (cons 71 0)
          (cons 72 2)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.90476190 -1.66666667 0.00000000)
          (cons 40  1.00000000)
          (cons 1 "VRT:")
          (cons 50  0.00000000)
          (cons 41  1.00000000)
          (cons 51  0.00000000)
          (cons 7 "Standard")
          (cons 71 0)
          (cons 72 2)
          (list 11 0.00000000 -1.66666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -1.19047619 -3.33333333 0.00000000)
          (cons 40  1.00000000)
          (cons 1 "E:")
          (cons 50  0.00000000)
          (cons 41  1.00000000)
          (cons 51  0.00000000)
          (cons 7 "Standard")
          (cons 71 0)
          (cons 72 2)
          (list 11 0.00000000 -3.33333333 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.33333333 -5.00000000 0.00000000)
          (cons 40  1.00000000)
          (cons 1 "OG:")
          (cons 50  0.00000000)
          (cons 41  1.00000000)
          (cons 51  0.00000000)
          (cons 7 "Standard")
          (cons 71 0)
          (cons 72 2)
          (list 11 0.00000000 -5.00000000 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 0.00000000 2.00000000 0.00000000)
          (cons 40  1.00000000)
          (cons 1 "")
          (cons 50  0.00000000)
          (cons 41  1.00000000)
          (cons 51  0.00000000)
          (cons 7 "Standard")
          (cons 71 0)
          (cons 72 1)
          (list 11 0.00000000 1.66666667 0.00000000)
          (list 210 0.00000000 0.00000000 1.00000000)
          (cons 100 "AcDbAttributeDefinition")
          (cons 280 0)
          (cons 3 "TITLE")
          (cons 2 "TITLE")
          (cons 70 0)
          (cons 73 0)
          (cons 74 1)
          (cons 280 0)
         )
         (list
          (cons 0 "ATTDEF")
          (cons 100 "AcDbEntity")
          (cons 67 0)
          (cons 8 "0")
          (cons 100 "AcDbText")
          (list 10 1.00000000 0.00000000 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "HOR")
          (cons 2 "HOR")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -1.66666667 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "VRT")
          (cons 2 "VRT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -3.33333333 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "E")
          (cons 2 "E")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -5.00000000 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "OG")
          (cons 2 "OG")
          (cons 70 0)
          (cons 73 0)
          (cons 74 0)
          (cons 280 0)
         )
         (list
          (cons 0 "TEXT")
          (cons 100 "AcDbEntity")
          (cons 67 0)
          (cons 8 "0")
          (cons 100 "AcDbText")
          (list 10 -5.09523810 -6.66666666 0.00000000)
          (cons 40  1.00000000)
          (cons 1 "CL OS:")
          (cons 50  0.00000000)
          (cons 41  1.00000000)
          (cons 51  0.00000000)
          (cons 7 "Standard")
          (cons 71 0)
          (cons 72 2)
          (list 11 0.00000000 -6.66666666 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 1.00000000 -6.66666666 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Centerline Offset")
          (cons 2 "CLOS")
          (cons 70 0)
          (cons 73 0)
          (cons 74 0)
          (cons 280 0)
         )
         (list (cons 0 "ENDBLK"))
        )
       )
       ((= (strcase BLKNAME) "RFLPROF")
        (list
         (list
          (cons 0 "BLOCK")
          (cons 2 "rflprof")
          (cons 70  2)
          (list 10 0.00000000 0.00000000 0.00000000)
         )
         (list
          (cons 0 "ATTDEF")
          (cons 100 "AcDbEntity")
          (cons 67 0)
          (cons 8 "0")
          (cons 100 "AcDbText")
          (list 10 -4.02380952 -29.25000000 0.00000000)
          (cons 40  2.50000000)
          (cons 1 "0")
          (cons 50  0.00000000)
          (cons 41  1.00000000)
          (cons 51  0.00000000)
          (cons 7 "Standard")
          (cons 71 0)
          (cons 72 2)
          (list 11 -2.00000000 -28.00000000 0.00000000)
          (list 210 0.00000000 0.00000000 1.00000000)
          (cons 100 "AcDbAttributeDefinition")
          (cons 280 0)
          (cons 3 "Station High")
          (cons 2 "STAH")
          (cons 70 0)
          (cons 73 0)
          (cons 74 2)
          (cons 280 0)
         )
         (list
          (cons 0 "ATTDEF")
          (cons 100 "AcDbEntity")
          (cons 67 0)
          (cons 8 "0")
          (cons 100 "AcDbText")
          (list 10 2.00000000 -29.25000000 0.00000000)
          (cons 40  2.50000000)
          (cons 1 "000")
          (cons 50  0.00000000)
          (cons 41  1.00000000)
          (cons 51  0.00000000)
          (cons 7 "Standard")
          (cons 71 0)
          (cons 72 0)
          (list 11 2.00000000 -28.00000000 0.00000000)
          (list 210 0.00000000 0.00000000 1.00000000)
          (cons 100 "AcDbAttributeDefinition")
          (cons 280 0)
          (cons 3 "Station Low")
          (cons 2 "STAL")
          (cons 70 0)
          (cons 73 0)
          (cons 74 2)
          (cons 280 0)
         )
         (list
          (cons 0 "ATTDEF")
          (cons 100 "AcDbEntity")
          (cons 67 0)
          (cons 8 "0")
          (cons 100 "AcDbText")
          (list 10 -15.00000000 -1.25000000 0.00000000)
          (cons 40  2.50000000)
          (cons 1 "0.0")
          (cons 50  0.00000000)
          (cons 41  1.00000000)
          (cons 51  0.00000000)
          (cons 7 "Standard")
          (cons 71 0)
          (cons 72 0)
          (list 11 -15.00000000 0.00000000 0.00000000)
          (list 210 0.00000000 0.00000000 1.00000000)
          (cons 100 "AcDbAttributeDefinition")
          (cons 280 0)
          (cons 3 "Elevation")
          (cons 2 "ELEV")
          (cons 70 0)
          (cons 73 0)
          (cons 74 2)
          (cons 280 0)
         )
         (list
          (cons 0 "ATTDEF")
          (cons 100 "AcDbEntity")
          (cons 67 0)
          (cons 8 "0")
          (cons 100 "AcDbText")
          (list 10 -10.59523810 -4.16666666 0.00000000)
          (cons 40  2.50000000)
          (cons 1 "1.0")
          (cons 50  0.00000000)
          (cons 41  1.00000000)
          (cons 51  0.00000000)
          (cons 7 "Standard")
          (cons 71 0)
          (cons 72 2)
          (list 11 -5.00000000 -4.16666666 0.00000000)
          (list 210 0.00000000 0.00000000 1.00000000)
          (cons 100 "AcDbAttributeDefinition")
          (cons 280 0)
          (cons 3 "Vertical Exageration")
          (cons 2 "VEXAG")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -7.02380952 -8.33333333 0.00000000)
          (cons 40  2.50000000)
          (cons 1 "0")
          (cons 50  0.00000000)
          (cons 41  1.00000000)
          (cons 51  0.00000000)
          (cons 7 "Standard")
          (cons 71 0)
          (cons 72 2)
          (list 11 -5.00000000 -8.33333333 0.00000000)
          (list 210 0.00000000 0.00000000 1.00000000)
          (cons 100 "AcDbAttributeDefinition")
          (cons 280 0)
          (cons 3 "Profile Layer")
          (cons 2 "PLAYER")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -7.02380952 -12.50000000 0.00000000)
          (cons 40  2.50000000)
          (cons 1 "0")
          (cons 50  0.00000000)
          (cons 41  1.00000000)
          (cons 51  0.00000000)
          (cons 7 "Standard")
          (cons 71 0)
          (cons 72 2)
          (list 11 -5.00000000 -12.50000000 0.00000000)
          (list 210 0.00000000 0.00000000 1.00000000)
          (cons 100 "AcDbAttributeDefinition")
          (cons 280 0)
          (cons 3 "Profile Text layer")
          (cons 2 "PTLAYER")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -5.00000000 -16.66666666 0.00000000)
          (cons 40  2.50000000)
          (cons 1 "")
          (cons 50  0.00000000)
          (cons 41  1.00000000)
          (cons 51  0.00000000)
          (cons 7 "Standard")
          (cons 71 0)
          (cons 72 2)
          (list 11 -5.00000000 -16.66666666 0.00000000)
          (list 210 0.00000000 0.00000000 1.00000000)
          (cons 100 "AcDbAttributeDefinition")
          (cons 280 0)
          (cons 3 "File Name")
          (cons 2 "FNAME")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -10.59523810 -20.83333333 0.00000000)
          (cons 40  2.50000000)
          (cons 1 "1.0")
          (cons 50  0.00000000)
          (cons 41  1.00000000)
          (cons 51  0.00000000)
          (cons 7 "Standard")
          (cons 71 0)
          (cons 72 2)
          (list 11 -5.00000000 -20.83333333 0.00000000)
          (list 210 0.00000000 0.00000000 1.00000000)
          (cons 100 "AcDbAttributeDefinition")
          (cons 280 0)
          (cons 3 "Scale")
          (cons 2 "SCALE")
          (cons 70 1)
          (cons 73 0)
          (cons 74 0)
          (cons 280 0)
         )
         (list
          (cons 0 "TEXT")
          (cons 100 "AcDbEntity")
          (cons 67 0)
          (cons 8 "0")
          (cons 100 "AcDbText")
          (list 10 -52.04761905 -1.25000000 0.00000000)
          (cons 40  2.50000000)
          (cons 1 "Datum elevation :")
          (cons 50  0.00000000)
          (cons 41  1.00000000)
          (cons 51  0.00000000)
          (cons 7 "Standard")
          (cons 71 0)
          (cons 72 2)
          (list 11 -18.00000000 0.00000000 0.00000000)
          (list 210 0.00000000 0.00000000 1.00000000)
          (cons 100 "AcDbText")
          (cons 73 2)
         )
         (list
          (cons 0 "TEXT")
          (cons 100 "AcDbEntity")
          (cons 67 0)
          (cons 8 "0")
          (cons 100 "AcDbText")
          (list 10 -1.54761905 -29.07142857 0.00000000)
          (cons 40  2.50000000)
          (cons 1 "+")
          (cons 50  0.00000000)
          (cons 41  1.00000000)
          (cons 51  0.00000000)
          (cons 7 "Standard")
          (cons 71 0)
          (cons 72 4)
          (list 11 0.00000000 -28.00000000 0.00000000)
          (list 210 0.00000000 0.00000000 1.00000000)
          (cons 100 "AcDbText")
          (cons 73 0)
         )
         (list
          (cons 0 "LINE")
          (cons 100 "AcDbEntity")
          (cons 67 0)
          (cons 8 "0")
          (cons 100 "AcDbLine")
          (list 10 0.00000000 0.00000000 0.00000000)
          (list 11 0.00000000 -25.00000000 0.00000000)
          (list 210 0.00000000 0.00000000 1.00000000)
         )
         (list
          (cons 0 "ARC")
          (cons 100 "AcDbEntity")
          (cons 67 0)
          (cons 8 "0")
          (cons 100 "AcDbCircle")
          (list 10 0.00000000 0.00000000 0.00000000)
          (cons 40  0.50000000)
          (list 210 0.00000000 0.00000000 1.00000000)
          (cons 100 "AcDbArc")
          (cons 50  1.57079633)
          (cons 51  0.00000000)
         )
         (list
          (cons 0 "ATTDEF")
          (cons 100 "AcDbEntity")
          (cons 67 0)
          (cons 8 "0")
          (cons 100 "AcDbText")
          (list 10 -6.30952381 -25.00000000 0.00000000)
          (cons 40  2.50000000)
          (cons 1 "1")
          (cons 50  0.00000000)
          (cons 41  1.00000000)
          (cons 51  0.00000000)
          (cons 7 "Standard")
          (cons 71 0)
          (cons 72 2)
          (list 11 -5.00000000 -25.00000000 0.00000000)
          (list 210 0.00000000 0.00000000 1.00000000)
          (cons 100 "AcDbAttributeDefinition")
          (cons 280 0)
          (cons 3 "Direction (1 = Forward, -1 = Reverse)")
          (cons 2 "DIRECTION")
          (cons 70 1)
          (cons 73 0)
          (cons 74 0)
          (cons 280 0)
         )
         (list (cons 0 "ENDBLK"))
        )
       )
       ((= (strcase BLKNAME) "RFLPROFVOLNODE")
        (list
         (list
          (cons 0 "BLOCK")
          (cons 2 "RFLProfVolNode")
          (cons 70  2)
          (cons 4 "")
          (list 10 0.00000000 0.00000000 0.00000000)
         )
         (list
          (cons 0 "ATTDEF")
          (cons 102 "{ACAD_XDICTIONARY")
          (cons 102 "}")
          (cons 100 "AcDbEntity")
          (cons 67 0)
          (cons 8 "0")
          (cons 100 "AcDbText")
          (list 10 -2.66941015 -3.53840878 0.00000000)
          (cons 40  7.00000000)
          (cons 1 "?")
          (cons 50  0.00000000)
          (cons 41  1.00000000)
          (cons 51  0.00000000)
          (cons 7 "BC Blocks Existing")
          (cons 71 0)
          (cons 72 4)
          (list 11 0.00000000 0.00000000 0.00000000)
          (list 210 0.00000000 0.00000000 1.00000000)
          (cons 100 "AcDbAttributeDefinition")
          (cons 280 0)
          (cons 3 "Volume")
          (cons 2 "VOLUME")
          (cons 70 0)
          (cons 73 0)
          (cons 74 0)
          (cons 280 1)
         )
         (list
          (cons 0 "ATTDEF")
          (cons 102 "{ACAD_XDICTIONARY")
          (cons 102 "}")
          (cons 100 "AcDbEntity")
          (cons 67 0)
          (cons 8 "Defpoints")
          (cons 100 "AcDbText")
          (list 10 39.14197531 0.96296296 0.00000000)
          (cons 40  0.50000000)
          (cons 1 "0.000")
          (cons 50  0.00000000)
          (cons 41  1.00000000)
          (cons 51  0.00000000)
          (cons 7 "BC Blocks Existing")
          (cons 71 0)
          (cons 72 4)
          (list 11 40.00000000 1.19855967 0.00000000)
          (list 210 0.00000000 0.00000000 1.00000000)
          (cons 100 "AcDbAttributeDefinition")
          (cons 280 0)
          (cons 3 "Start Station")
          (cons 2 "START")
          (cons 70 1)
          (cons 73 0)
          (cons 74 0)
          (cons 280 1)
         )
         (list
          (cons 0 "ATTDEF")
          (cons 102 "{ACAD_XDICTIONARY")
          (cons 102 "}")
          (cons 100 "AcDbEntity")
          (cons 67 0)
          (cons 8 "Defpoints")
          (cons 100 "AcDbText")
          (list 10 39.14197531 0.16392318 0.00000000)
          (cons 40  0.50000000)
          (cons 1 "0.000")
          (cons 50  0.00000000)
          (cons 41  1.00000000)
          (cons 51  0.00000000)
          (cons 7 "BC Blocks Existing")
          (cons 71 0)
          (cons 72 4)
          (list 11 40.00000000 0.39951989 0.00000000)
          (list 210 0.00000000 0.00000000 1.00000000)
          (cons 100 "AcDbAttributeDefinition")
          (cons 280 0)
          (cons 3 "End Station")
          (cons 2 "END")
          (cons 70 1)
          (cons 73 0)
          (cons 74 0)
          (cons 280 1)
         )
         (list
          (cons 0 "ATTDEF")
          (cons 102 "{ACAD_XDICTIONARY")
          (cons 102 "}")
          (cons 100 "AcDbEntity")
          (cons 67 0)
          (cons 8 "Defpoints")
          (cons 100 "AcDbText")
          (list 10 39.29526749 -0.64574760 0.00000000)
          (cons 40  0.50000000)
          (cons 1 "CUT")
          (cons 50  0.00000000)
          (cons 41  1.00000000)
          (cons 51  0.00000000)
          (cons 7 "BC Blocks Existing")
          (cons 71 0)
          (cons 72 4)
          (list 11 40.00000000 -0.39951989 0.00000000)
          (list 210 0.00000000 0.00000000 1.00000000)
          (cons 100 "AcDbAttributeDefinition")
          (cons 280 0)
          (cons 3 "Material Name (or CUT / FILL)")
          (cons 2 "MATERIAL")
          (cons 70 1)
          (cons 73 0)
          (cons 74 0)
          (cons 280 1)
         )
         (list
          (cons 0 "ATTDEF")
          (cons 102 "{ACAD_XDICTIONARY")
          (cons 102 "}")
          (cons 100 "AcDbEntity")
          (cons 67 0)
          (cons 8 "Defpoints")
          (cons 100 "AcDbText")
          (list 10 36.47393690 -1.44067215 0.00000000)
          (cons 40  0.50000000)
          (cons 1 "<include .xml in name>")
          (cons 50  0.00000000)
          (cons 41  1.00000000)
          (cons 51  0.00000000)
          (cons 7 "BC Blocks Existing")
          (cons 71 0)
          (cons 72 4)
          (list 11 40.00000000 -1.19855967 0.00000000)
          (list 210 0.00000000 0.00000000 1.00000000)
          (cons 100 "AcDbAttributeDefinition")
          (cons 280 0)
          (cons 3 "XML File Name")
          (cons 2 "FILE")
          (cons 70 1)
          (cons 73 0)
          (cons 74 0)
          (cons 280 1)
         )
         (list (cons 0 "ENDBLK"))
        )
       )
       ((= (strcase BLKNAME) "RFLSURVEY")
        (list
         (list
          (cons 0 "BLOCK")
          (cons 2 "RFLSURVEY")
          (cons 70  2)
          (cons 4 "")
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "TEXT")
          (cons 102 "{ACAD_XDICTIONARY")
          (cons 102 "}")
          (cons 100 "AcDbEntity")
          (cons 67 0)
          (cons 8 "0")
          (cons 100 "AcDbText")
          (list 10 -18.64285714 5.25000000 0.00000000)
          (cons 40  1.50000000)
          (cons 1 "Local Northing")
          (cons 50  0.00000000)
          (cons 41  1.00000000)
          (cons 51  0.00000000)
          (cons 7 "Standard")
          (cons 71 0)
          (cons 72 2)
          (list 11 -2.50000000 6.00000000 0.00000000)
          (list 210 0.00000000 0.00000000 1.00000000)
          (cons 100 "AcDbText")
          (cons 73 2)
         )
         (list
          (cons 0 "TEXT")
          (cons 102 "{ACAD_XDICTIONARY")
          (cons 102 "}")
          (cons 100 "AcDbEntity")
          (cons 67 0)
          (cons 8 "0")
          (cons 100 "AcDbText")
          (list 10 -17.35714286 3.25000000 0.00000000)
          (cons 40  1.50000000)
          (cons 1 "Local Easting")
          (cons 50  0.00000000)
          (cons 41  1.00000000)
          (cons 51  0.00000000)
          (cons 7 "Standard")
          (cons 71 0)
          (cons 72 2)
          (list 11 -2.50000000 4.00000000 0.00000000)
          (list 210 0.00000000 0.00000000 1.00000000)
          (cons 100 "AcDbText")
          (cons 73 2)
         )
         (list
          (cons 0 "TEXT")
          (cons 102 "{ACAD_XDICTIONARY")
          (cons 102 "}")
          (cons 100 "AcDbEntity")
          (cons 67 0)
          (cons 8 "0")
          (cons 100 "AcDbText")
          (list 10 -17.21428571 1.25000000 0.00000000)
          (cons 40  1.50000000)
          (cons 1 "Grid Northing")
          (cons 50  0.00000000)
          (cons 41  1.00000000)
          (cons 51  0.00000000)
          (cons 7 "Standard")
          (cons 71 0)
          (cons 72 2)
          (list 11 -2.50000000 2.00000000 0.00000000)
          (list 210 0.00000000 0.00000000 1.00000000)
          (cons 100 "AcDbText")
          (cons 73 2)
         )
         (list
          (cons 0 "TEXT")
          (cons 102 "{ACAD_XDICTIONARY")
          (cons 102 "}")
          (cons 100 "AcDbEntity")
          (cons 67 0)
          (cons 8 "0")
          (cons 100 "AcDbText")
          (list 10 -15.92857143 -0.75000000 0.00000000)
          (cons 40  1.50000000)
          (cons 1 "Grid Easting")
          (cons 50  0.00000000)
          (cons 41  1.00000000)
          (cons 51  0.00000000)
          (cons 7 "Standard")
          (cons 71 0)
          (cons 72 2)
          (list 11 -2.50000000 0.00000000 0.00000000)
          (list 210 0.00000000 0.00000000 1.00000000)
          (cons 100 "AcDbText")
          (cons 73 2)
         )
         (list
          (cons 0 "TEXT")
          (cons 102 "{ACAD_XDICTIONARY")
          (cons 102 "}")
          (cons 100 "AcDbEntity")
          (cons 67 0)
          (cons 8 "0")
          (cons 100 "AcDbText")
          (list 10 -16.64285714 -2.75000000 0.00000000)
          (cons 40  1.50000000)
          (cons 1 "Scale Factor")
          (cons 50  0.00000000)
          (cons 41  1.00000000)
          (cons 51  0.00000000)
          (cons 7 "Standard")
          (cons 71 0)
          (cons 72 2)
          (list 11 -2.50000000 -2.00000000 0.00000000)
          (list 210 0.00000000 0.00000000 1.00000000)
          (cons 100 "AcDbText")
          (cons 73 2)
         )
         (list
          (cons 0 "TEXT")
          (cons 102 "{ACAD_XDICTIONARY")
          (cons 102 "}")
          (cons 100 "AcDbEntity")
          (cons 67 0)
          (cons 8 "0")
          (cons 100 "AcDbText")
          (list 10 -13.14285714 -4.75000000 0.00000000)
          (cons 40  1.50000000)
          (cons 1 "Zone LNG")
          (cons 50  0.00000000)
          (cons 41  1.00000000)
          (cons 51  0.00000000)
          (cons 7 "Standard")
          (cons 71 0)
          (cons 72 2)
          (list 11 -2.50000000 -4.00000000 0.00000000)
          (list 210 0.00000000 0.00000000 1.00000000)
          (cons 100 "AcDbText")
          (cons 73 2)
         )
         (list
          (cons 0 "TEXT")
          (cons 102 "{ACAD_XDICTIONARY")
          (cons 102 "}")
          (cons 100 "AcDbEntity")
          (cons 67 0)
          (cons 8 "0")
          (cons 100 "AcDbText")
          (list 10 -13.07142857 -6.75000000 0.00000000)
          (cons 40  1.50000000)
          (cons 1 "Zone LAT")
          (cons 50  0.00000000)
          (cons 41  1.00000000)
          (cons 51  0.00000000)
          (cons 7 "Standard")
          (cons 71 0)
          (cons 72 2)
          (list 11 -2.50000000 -6.00000000 0.00000000)
          (list 210 0.00000000 0.00000000 1.00000000)
          (cons 100 "AcDbText")
          (cons 73 2)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 5.25000000 0.00000000)
          (cons 40  1.50000000)
          (cons 1 "")
          (cons 50  0.00000000)
          (cons 41  1.00000000)
          (cons 51  0.00000000)
          (cons 7 "Standard")
          (cons 71 0)
          (cons 72 0)
          (list 11 2.50000000 6.00000000 0.00000000)
          (list 210 0.00000000 0.00000000 1.00000000)
          (cons 100 "AcDbAttributeDefinition")
          (cons 280 0)
          (cons 3 "Local Northing")
          (cons 2 "LOCALNORTHING")
          (cons 70 0)
          (cons 73 0)
          (cons 74 2)
          (cons 280 1)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 3.25000000 0.00000000)
          (cons 40  1.50000000)
          (cons 1 "")
          (cons 50  0.00000000)
          (cons 41  1.00000000)
          (cons 51  0.00000000)
          (cons 7 "Standard")
          (cons 71 0)
          (cons 72 0)
          (list 11 2.50000000 4.00000000 0.00000000)
          (list 210 0.00000000 0.00000000 1.00000000)
          (cons 100 "AcDbAttributeDefinition")
          (cons 280 0)
          (cons 3 "Local Easting")
          (cons 2 "LOCALEASTING")
          (cons 70 0)
          (cons 73 0)
          (cons 74 2)
          (cons 280 1)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 1.25000000 0.00000000)
          (cons 40  1.50000000)
          (cons 1 "")
          (cons 50  0.00000000)
          (cons 41  1.00000000)
          (cons 51  0.00000000)
          (cons 7 "Standard")
          (cons 71 0)
          (cons 72 0)
          (list 11 2.50000000 2.00000000 0.00000000)
          (list 210 0.00000000 0.00000000 1.00000000)
          (cons 100 "AcDbAttributeDefinition")
          (cons 280 0)
          (cons 3 "Grid Northing")
          (cons 2 "GRIDNORTHING")
          (cons 70 0)
          (cons 73 0)
          (cons 74 2)
          (cons 280 1)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 -0.75000000 0.00000000)
          (cons 40  1.50000000)
          (cons 1 "")
          (cons 50  0.00000000)
          (cons 41  1.00000000)
          (cons 51  0.00000000)
          (cons 7 "Standard")
          (cons 71 0)
          (cons 72 0)
          (list 11 2.50000000 0.00000000 0.00000000)
          (list 210 0.00000000 0.00000000 1.00000000)
          (cons 100 "AcDbAttributeDefinition")
          (cons 280 0)
          (cons 3 "Grid Easting")
          (cons 2 "GRIDEASTING")
          (cons 70 0)
          (cons 73 0)
          (cons 74 2)
          (cons 280 1)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 -2.75000000 0.00000000)
          (cons 40  1.50000000)
          (cons 1 "")
          (cons 50  0.00000000)
          (cons 41  1.00000000)
          (cons 51  0.00000000)
          (cons 7 "Standard")
          (cons 71 0)
          (cons 72 0)
          (list 11 2.50000000 -2.00000000 0.00000000)
          (list 210 0.00000000 0.00000000 1.00000000)
          (cons 100 "AcDbAttributeDefinition")
          (cons 280 0)
          (cons 3 "Scale Factor")
          (cons 2 "SCALEFACTOR")
          (cons 70 0)
          (cons 73 0)
          (cons 74 2)
          (cons 280 1)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 -4.75000000 0.00000000)
          (cons 40  1.50000000)
          (cons 1 "10")
          (cons 50  0.00000000)
          (cons 41  1.00000000)
          (cons 51  0.00000000)
          (cons 7 "Standard")
          (cons 71 0)
          (cons 72 0)
          (list 11 2.50000000 -4.00000000 0.00000000)
          (list 210 0.00000000 0.00000000 1.00000000)
          (cons 100 "AcDbAttributeDefinition")
          (cons 280 0)
          (cons 3 "Zone Longitude (i.e. 10)")
          (cons 2 "ZONELNG")
          (cons 70 0)
          (cons 73 0)
          (cons 74 2)
          (cons 280 1)
         )
         (list
          (cons 0 "ATTDEF")
          (cons 102 "{ACAD_XDICTIONARY")
          (cons 102 "}")
          (cons 100 "AcDbEntity")
          (cons 67 0)
          (cons 8 "0")
          (cons 100 "AcDbText")
          (list 10 2.50000000 -6.75000000 0.00000000)
          (cons 40  1.50000000)
          (cons 1 "U")
          (cons 50  0.00000000)
          (cons 41  1.00000000)
          (cons 51  0.00000000)
          (cons 7 "Standard")
          (cons 71 0)
          (cons 72 0)
          (list 11 2.50000000 -6.00000000 0.00000000)
          (list 210 0.00000000 0.00000000 1.00000000)
          (cons 100 "AcDbAttributeDefinition")
          (cons 280 0)
          (cons 3 "Zone Latitude (i.e. U)")
          (cons 2 "ZONELAT")
          (cons 70 0)
          (cons 73 0)
          (cons 74 2)
          (cons 280 1)
         )
         (list (cons 0 "ENDBLK"))
        )
       )
       ((= (strcase BLKNAME) "RFLTRAIN")
        (list
         (list
          (cons 0 "BLOCK")
          (cons 2 "RFLTrain")
          (cons 70  2)
          (cons 4 "")
          (list 10 0.00000000 0.00000000 0.00000000)
         )
         (list
          (cons 0 "TEXT")
          (cons 100 "AcDbEntity")
          (cons 67 0)
          (cons 8 "0")
          (cons 100 "AcDbText")
          (list 10 -17.85714286 -1.66666667 0.00000000)
          (cons 40  1.00000000)
          (cons 1 "Rail C/L to C/L (mm):")
          (cons 50  0.00000000)
          (cons 41  1.00000000)
          (cons 51  0.00000000)
          (cons 7 "Standard")
          (cons 71 0)
          (cons 72 2)
          (list 11 0.00000000 -1.66666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -13.33333333 -3.33333334 0.00000000)
          (cons 40  1.00000000)
          (cons 1 "Rail Gauge (mm):")
          (cons 50  0.00000000)
          (cons 41  1.00000000)
          (cons 51  0.00000000)
          (cons 7 "Standard")
          (cons 71 0)
          (cons 72 2)
          (list 11 0.00000000 -3.33333334 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -30.61904762 -8.33333334 0.00000000)
          (cons 40  1.00000000)
          (cons 1 "Inswing/Outswing Label Point 'X' (D.U.):")
          (cons 50  0.00000000)
          (cons 41  1.00000000)
          (cons 51  0.00000000)
          (cons 7 "Standard")
          (cons 71 0)
          (cons 72 2)
          (list 11 0.00000000 -8.33333334 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -30.61904762 -10.00000001 0.00000000)
          (cons 40  1.00000000)
          (cons 1 "Inswing/Outswing Label Point 'Y' (D.U.):")
          (cons 50  0.00000000)
          (cons 41  1.00000000)
          (cons 51  0.00000000)
          (cons 7 "Standard")
          (cons 71 0)
          (cons 72 2)
          (list 11 0.00000000 -10.00000001 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -12.00000000 -5.00000001 0.00000000)
          (cons 40  1.00000000)
          (cons 1 "Vehicle WB (m):")
          (cons 50  0.00000000)
          (cons 41  1.00000000)
          (cons 51  0.00000000)
          (cons 7 "Standard")
          (cons 71 0)
          (cons 72 2)
          (list 11 0.00000000 -5.00000001 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -16.76190476 -6.66666668 0.00000000)
          (cons 40  1.00000000)
          (cons 1 "Vehicle Overhang (m):")
          (cons 50  0.00000000)
          (cons 41  1.00000000)
          (cons 51  0.00000000)
          (cons 7 "Standard")
          (cons 71 0)
          (cons 72 2)
          (list 11 0.00000000 -6.66666668 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -28.42857143 -11.66666667 0.00000000)
          (cons 40  1.00000000)
          (cons 1 "Superelevation Label Point 'X' (D.U.):")
          (cons 50  0.00000000)
          (cons 41  1.00000000)
          (cons 51  0.00000000)
          (cons 7 "Standard")
          (cons 71 0)
          (cons 72 2)
          (list 11 0.00000000 -11.66666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -17.33333333 -13.33333333 0.00000000)
          (cons 40  1.00000000)
          (cons 1 "Label Offset 'X' (D.U.):")
          (cons 50  0.00000000)
          (cons 41  1.00000000)
          (cons 51  0.00000000)
          (cons 7 "Standard")
          (cons 71 0)
          (cons 72 2)
          (list 11 0.00000000 -13.33333333 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -17.33333333 -15.00000000 0.00000000)
          (cons 40  1.00000000)
          (cons 1 "Label Offset 'Y' (D.U.):")
          (cons 50  0.00000000)
          (cons 41  1.00000000)
          (cons 51  0.00000000)
          (cons 7 "Standard")
          (cons 71 0)
          (cons 72 2)
          (list 11 0.00000000 -15.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -18.90476190 -16.66666667 0.00000000)
          (cons 40  1.00000000)
          (cons 1 "Label Title Height (D.U.):")
          (cons 50  0.00000000)
          (cons 41  1.00000000)
          (cons 51  0.00000000)
          (cons 7 "Standard")
          (cons 71 0)
          (cons 72 2)
          (list 11 0.00000000 -16.66666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -18.95238095 -18.33333334 0.00000000)
          (cons 40  1.00000000)
          (cons 1 "Label Text Height (D.U.):")
          (cons 50  0.00000000)
          (cons 41  1.00000000)
          (cons 51  0.00000000)
          (cons 7 "Standard")
          (cons 71 0)
          (cons 72 2)
          (list 11 0.00000000 -18.33333334 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -13.00000000 -20.00000001 0.00000000)
          (cons 40  1.00000000)
          (cons 1 "Line Layer Suffix:")
          (cons 50  0.00000000)
          (cons 41  1.00000000)
          (cons 51  0.00000000)
          (cons 7 "Standard")
          (cons 71 0)
          (cons 72 2)
          (list 11 0.00000000 -20.00000001 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -17.61904762 -21.66666668 0.00000000)
          (cons 40  1.00000000)
          (cons 1 "Dimension Layer Suffix:")
          (cons 50  0.00000000)
          (cons 41  1.00000000)
          (cons 51  0.00000000)
          (cons 7 "Standard")
          (cons 71 0)
          (cons 72 2)
          (list 11 0.00000000 -21.66666668 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -13.23809524 -23.33333335 0.00000000)
          (cons 40  1.00000000)
          (cons 1 "Text Layer Suffix:")
          (cons 50  0.00000000)
          (cons 41  1.00000000)
          (cons 51  0.00000000)
          (cons 7 "Standard")
          (cons 71 0)
          (cons 72 2)
          (list 11 0.00000000 -23.33333335 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -15.61904762 -26.66666669 0.00000000)
          (cons 40  1.00000000)
          (cons 1 "Section Block Name:")
          (cons 50  0.00000000)
          (cons 41  1.00000000)
          (cons 51  0.00000000)
          (cons 7 "Standard")
          (cons 71 0)
          (cons 72 2)
          (list 11 0.00000000 -26.66666669 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -26.57142857 -28.33333336 0.00000000)
          (cons 40  1.00000000)
          (cons 1 "Left Dynamic Section Block Name:")
          (cons 50  0.00000000)
          (cons 41  1.00000000)
          (cons 51  0.00000000)
          (cons 7 "Standard")
          (cons 71 0)
          (cons 72 2)
          (list 11 0.00000000 -28.33333336 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -27.52380952 -30.00000003 0.00000000)
          (cons 40  1.00000000)
          (cons 1 "Right Dynamic Section Block Name:")
          (cons 50  0.00000000)
          (cons 41  1.00000000)
          (cons 51  0.00000000)
          (cons 7 "Standard")
          (cons 71 0)
          (cons 72 2)
          (list 11 0.00000000 -30.00000003 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -23.90476190 -25.00000002 0.00000000)
          (cons 40  1.00000000)
          (cons 1 "Section Reference Block Name:")
          (cons 50  0.00000000)
          (cons 41  1.00000000)
          (cons 51  0.00000000)
          (cons 7 "Standard")
          (cons 71 0)
          (cons 72 2)
          (list 11 0.00000000 -25.00000002 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 -16.21428571 0.50000000 0.00000000)
          (cons 40  1.50000000)
          (cons 1 "RFL Quick Train Initialization")
          (cons 50  0.00000000)
          (cons 41  1.00000000)
          (cons 51  0.00000000)
          (cons 7 "Standard")
          (cons 71 0)
          (cons 72 1)
          (list 11 0.00000000 0.00000000 0.00000000)
          (list 210 0.00000000 0.00000000 1.00000000)
          (cons 100 "AcDbAttributeDefinition")
          (cons 280 0)
          (cons 3 "TITLE")
          (cons 2 "TITLE")
          (cons 70 0)
          (cons 73 0)
          (cons 74 1)
          (cons 280 0)
         )
         (list
          (cons 0 "ATTDEF")
          (cons 100 "AcDbEntity")
          (cons 67 0)
          (cons 8 "0")
          (cons 100 "AcDbText")
          (list 10 1.00000000 -1.66666667 0.00000000)
          (cons 40  1.00000000)
          (cons 1 "1503.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Rail C/L to C/L (mm)")
          (cons 2 "RAILCL")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -3.33333334 0.00000000)
          (cons 40  1.00000000)
          (cons 1 "1435.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Rail Gauge (mm)")
          (cons 2 "GAUGE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -5.00000001 0.00000000)
          (cons 40  1.00000000)
          (cons 1 "12.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vehicle WB (m)")
          (cons 2 "WB")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -6.66666668 0.00000000)
          (cons 40  1.00000000)
          (cons 1 "2.50")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vehicle Overhang (m)")
          (cons 2 "OH")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -8.33333334 0.00000000)
          (cons 40  1.00000000)
          (cons 1 "1.592")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Inswing/Outswing Label Point 'X' (D.U.)")
          (cons 2 "LABELIOX")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -10.00000001 0.00000000)
          (cons 40  1.00000000)
          (cons 1 "2.734")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Inswing/Outswing Label Point 'Y' (D.U.)")
          (cons 2 "LABELIOY")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -11.66666667 0.00000000)
          (cons 40  1.00000000)
          (cons 1 "-1.5")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Superelevation Label Point 'X' (D.U.)")
          (cons 2 "LABELSX")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -13.33333333 0.00000000)
          (cons 40  1.00000000)
          (cons 1 "2.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Label Offset 'X' (D.U.)")
          (cons 2 "LABELOSX")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -15.00000000 0.00000000)
          (cons 40  1.00000000)
          (cons 1 "0.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Label Offset 'Y' (D.U.)")
          (cons 2 "LABELOSY")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -16.66666667 0.00000000)
          (cons 40  1.00000000)
          (cons 1 "0.15")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Label Title Height (D.U.)")
          (cons 2 "LTITLEH")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -18.33333334 0.00000000)
          (cons 40  1.00000000)
          (cons 1 "0.10")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Label Text Height (D.U.)")
          (cons 2 "LTEXTH")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -20.00000001 0.00000000)
          (cons 40  1.00000000)
          (cons 1 "-LINE")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Line Layer Suffix")
          (cons 2 "LLAYERS")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -21.66666668 0.00000000)
          (cons 40  1.00000000)
          (cons 1 "-DIM")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Dimension Layer Suffix")
          (cons 2 "DLAYERS")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -23.33333335 0.00000000)
          (cons 40  1.00000000)
          (cons 1 "-TXT")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Layer Suffix")
          (cons 2 "TLAYERS")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -25.00000002 0.00000000)
          (cons 40  1.00000000)
          (cons 1 "SECT-REF")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Section Reference Block Name")
          (cons 2 "REFSECTION")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -26.66666669 0.00000000)
          (cons 40  1.00000000)
          (cons 1 "TRAINSECTION")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Section Block Name")
          (cons 2 "SECTION")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -28.33333336 0.00000000)
          (cons 40  1.00000000)
          (cons 1 "LTRAINSECTION")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Left Dynamic Section Block Name")
          (cons 2 "LSECTION")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -30.00000003 0.00000000)
          (cons 40  1.00000000)
          (cons 1 "RTRAINSECTION")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Right Dynamic Section Block Name")
          (cons 2 "RSECTION")
          (cons 70 0)
          (cons 73 0)
          (cons 74 0)
          (cons 280 0)
         )
         (list
          (cons 0 "TEXT")
          (cons 100 "AcDbEntity")
          (cons 67 0)
          (cons 8 "0")
          (cons 100 "AcDbText")
          (list 10 -21.47619048 -31.66666670 0.00000000)
          (cons 40  1.00000000)
          (cons 1 "Section Grouping Tollerance:")
          (cons 50  0.00000000)
          (cons 41  1.00000000)
          (cons 51  0.00000000)
          (cons 7 "Standard")
          (cons 71 0)
          (cons 72 2)
          (list 11 0.00000000 -31.66666670 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 1.00000000 -31.66666670 0.00000000)
          (cons 40  1.00000000)
          (cons 1 "0.500")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Cross Section Grouping Tollerance")
          (cons 2 "GROUPTOL")
          (cons 70 0)
          (cons 73 0)
          (cons 74 0)
          (cons 280 0)
         )
         (list
          (cons 0 "TEXT")
          (cons 100 "AcDbEntity")
          (cons 67 0)
          (cons 8 "0")
          (cons 100 "AcDbText")
          (list 10 -18.47619048 -33.33333337 0.00000000)
          (cons 40  1.00000000)
          (cons 1 "Section Draw Increment:")
          (cons 50  0.00000000)
          (cons 41  1.00000000)
          (cons 51  0.00000000)
          (cons 7 "Standard")
          (cons 71 0)
          (cons 72 2)
          (list 11 0.00000000 -33.33333337 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 1.00000000 -33.33333337 0.00000000)
          (cons 40  1.00000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Section Draw Increment")
          (cons 2 "SECTINC")
          (cons 70 0)
          (cons 73 0)
          (cons 74 0)
          (cons 280 0)
         )
         (list (cons 0 "ENDBLK"))
        )
       )
       ((= (strcase BLKNAME) "ROUNDABOUT")
        (list
         (list
          (cons 0 "BLOCK")
          (cons 2 "ROUNDABOUT")
          (cons 70  2)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  1.00000000)
          (list 210 0.00000000 0.00000000 1.00000000)
         )
         (list
          (cons 0 "LWPOLYLINE")
          (cons 100 "AcDbEntity")
          (cons 67 0)
          (cons 8 "0")
          (cons 100 "AcDbPolyline")
          (cons 90 3)
          (cons 70 128)
          (cons 38  0.00000000)
          (cons 39  0.00000000)
          (list 10 1.00000000 0.00000000)
          (cons 40  0.00000000)
          (cons 41  0.00000000)
          (cons 42  0.00000000)
          (cons 91 0)
          (list 10 2.00000000 0.00000000)
          (cons 40  1.00000000)
          (cons 41  0.00000000)
          (cons 42  0.00000000)
          (cons 91 0)
          (list 10 3.00000000 0.00000000)
          (cons 40  0.00000000)
          (cons 41  0.00000000)
          (cons 42  0.00000000)
          (cons 91 0)
          (list 210 0.00000000 0.00000000 1.00000000)
         )
         (list
          (cons 0 "ATTDEF")
          (cons 100 "AcDbEntity")
          (cons 67 0)
          (cons 8 "0")
          (cons 100 "AcDbText")
          (list 10 -2.22619048 1.36904762 0.00000000)
          (cons 40  0.50000000)
          (cons 1 "Roundabout")
          (cons 50  0.00000000)
          (cons 41  1.00000000)
          (cons 51  0.00000000)
          (cons 7 "Standard")
          (cons 71 0)
          (cons 72 4)
          (list 11 0.00000000 1.61904762 0.00000000)
          (list 210 0.00000000 0.00000000 1.00000000)
          (cons 100 "AcDbAttributeDefinition")
          (cons 280 0)
          (cons 3 "Name")
          (cons 2 "NAME")
          (cons 70 0)
          (cons 73 0)
          (cons 74 0)
          (cons 280 1)
         )
         (list
          (cons 0 "ATTDEF")
          (cons 100 "AcDbEntity")
          (cons 67 0)
          (cons 8 "0")
          (cons 100 "AcDbText")
          (list 10 -0.59523810 -0.25000000 0.00000000)
          (cons 40  0.50000000)
          (cons 1 "0.0")
          (cons 50  0.00000000)
          (cons 41  1.00000000)
          (cons 51  0.00000000)
          (cons 7 "Standard")
          (cons 71 0)
          (cons 72 4)
          (list 11 0.00000000 0.00000000 0.00000000)
          (list 210 0.00000000 0.00000000 1.00000000)
          (cons 100 "AcDbAttributeDefinition")
          (cons 280 0)
          (cons 3 "Slope (%)")
          (cons 2 "SLOPE")
          (cons 70 0)
          (cons 73 0)
          (cons 74 0)
          (cons 280 1)
         )
         (list
          (cons 0 "ATTDEF")
          (cons 100 "AcDbEntity")
          (cons 67 0)
          (cons 8 "0")
          (cons 100 "AcDbText")
          (list 10 -0.59523810 -1.05952381 0.00000000)
          (cons 40  0.50000000)
          (cons 1 "0.0")
          (cons 50  0.00000000)
          (cons 41  1.00000000)
          (cons 51  0.00000000)
          (cons 7 "Standard")
          (cons 71 0)
          (cons 72 4)
          (list 11 0.00000000 -0.80952381 0.00000000)
          (list 210 0.00000000 0.00000000 1.00000000)
          (cons 100 "AcDbAttributeDefinition")
          (cons 280 0)
          (cons 3 "Center (Plane) Elevation")
          (cons 2 "ELEV")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.59523810 -1.86904762 0.00000000)
          (cons 40  0.50000000)
          (cons 1 "2.0")
          (cons 50  0.00000000)
          (cons 41  1.00000000)
          (cons 51  0.00000000)
          (cons 7 "Standard")
          (cons 71 0)
          (cons 72 4)
          (list 11 0.00000000 -1.61904762 0.00000000)
          (list 210 0.00000000 0.00000000 1.00000000)
          (cons 100 "AcDbAttributeDefinition")
          (cons 280 0)
          (cons 3 "Circulatory Grade (%)")
          (cons 2 "GRADE")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.59523810 -2.67857143 0.00000000)
          (cons 40  0.50000000)
          (cons 1 "3.0")
          (cons 50  0.00000000)
          (cons 41  1.00000000)
          (cons 51  0.00000000)
          (cons 7 "Standard")
          (cons 71 0)
          (cons 72 4)
          (list 11 0.00000000 -2.42857143 0.00000000)
          (list 210 0.00000000 0.00000000 1.00000000)
          (cons 100 "AcDbAttributeDefinition")
          (cons 280 0)
          (cons 3 "Inner Grade (%)")
          (cons 2 "INNERGRADE")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.86904762 -3.48809524 0.00000000)
          (cons 40  0.50000000)
          (cons 1 "10.0")
          (cons 50  0.00000000)
          (cons 41  1.00000000)
          (cons 51  0.00000000)
          (cons 7 "Standard")
          (cons 71 0)
          (cons 72 4)
          (list 11 0.00000000 -3.23809524 0.00000000)
          (list 210 0.00000000 0.00000000 1.00000000)
          (cons 100 "AcDbAttributeDefinition")
          (cons 280 0)
          (cons 3 "Center Grade (%)")
          (cons 2 "CENTERGRADE")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.83333333 -4.29761905 0.00000000)
          (cons 40  0.50000000)
          (cons 1 "30.0")
          (cons 50  0.00000000)
          (cons 41  1.00000000)
          (cons 51  0.00000000)
          (cons 7 "Standard")
          (cons 71 0)
          (cons 72 4)
          (list 11 0.00000000 -4.04761905 0.00000000)
          (list 210 0.00000000 0.00000000 1.00000000)
          (cons 100 "AcDbAttributeDefinition")
          (cons 280 0)
          (cons 3 "Outer Radius")
          (cons 2 "ROUT")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.86904762 -5.10714286 0.00000000)
          (cons 40  0.50000000)
          (cons 1 "10.0")
          (cons 50  0.00000000)
          (cons 41  1.00000000)
          (cons 51  0.00000000)
          (cons 7 "Standard")
          (cons 71 0)
          (cons 72 4)
          (list 11 0.00000000 -4.85714286 0.00000000)
          (list 210 0.00000000 0.00000000 1.00000000)
          (cons 100 "AcDbAttributeDefinition")
          (cons 280 0)
          (cons 3 "Inner Radius")
          (cons 2 "RIN")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.59523810 -5.91666667 0.00000000)
          (cons 40  0.50000000)
          (cons 1 "2.5")
          (cons 50  0.00000000)
          (cons 41  1.00000000)
          (cons 51  0.00000000)
          (cons 7 "Standard")
          (cons 71 0)
          (cons 72 4)
          (list 11 0.00000000 -5.66666667 0.00000000)
          (list 210 0.00000000 0.00000000 1.00000000)
          (cons 100 "AcDbAttributeDefinition")
          (cons 280 0)
          (cons 3 "Center Radius")
          (cons 2 "RCENTER")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.59523810 -6.72619048 0.00000000)
          (cons 40  0.50000000)
          (cons 1 "3.0")
          (cons 50  0.00000000)
          (cons 41  1.00000000)
          (cons 51  0.00000000)
          (cons 7 "Standard")
          (cons 71 0)
          (cons 72 4)
          (list 11 0.00000000 -6.47619048 0.00000000)
          (list 210 0.00000000 0.00000000 1.00000000)
          (cons 100 "AcDbAttributeDefinition")
          (cons 280 0)
          (cons 3 "Fill Slope (X:1)")
          (cons 2 "FILL")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.59523810 -7.53571429 0.00000000)
          (cons 40  0.50000000)
          (cons 1 "3.0")
          (cons 50  0.00000000)
          (cons 41  1.00000000)
          (cons 51  0.00000000)
          (cons 7 "Standard")
          (cons 71 0)
          (cons 72 4)
          (list 11 0.00000000 -7.28571429 0.00000000)
          (list 210 0.00000000 0.00000000 1.00000000)
          (cons 100 "AcDbAttributeDefinition")
          (cons 280 0)
          (cons 3 "Cut Slope (X:1)")
          (cons 2 "CUT")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.59523810 -8.34523810 0.00000000)
          (cons 40  0.50000000)
          (cons 1 "3.0")
          (cons 50  0.00000000)
          (cons 41  1.00000000)
          (cons 51  0.00000000)
          (cons 7 "Standard")
          (cons 71 0)
          (cons 72 4)
          (list 11 0.00000000 -8.09523810 0.00000000)
          (list 210 0.00000000 0.00000000 1.00000000)
          (cons 100 "AcDbAttributeDefinition")
          (cons 280 0)
          (cons 3 "Ditch Back Slope (X:1)")
          (cons 2 "CUTDITCHSLOPE")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.63095238 -9.15476190 0.00000000)
          (cons 40  0.50000000)
          (cons 1 "1.0")
          (cons 50  0.00000000)
          (cons 41  1.00000000)
          (cons 51  0.00000000)
          (cons 7 "Standard")
          (cons 71 0)
          (cons 72 4)
          (list 11 0.00000000 -8.90476190 0.00000000)
          (list 210 0.00000000 0.00000000 1.00000000)
          (cons 100 "AcDbAttributeDefinition")
          (cons 280 0)
          (cons 3 "Ditch Depth")
          (cons 2 "CUTDITCHDEPTH")
          (cons 70 1)
          (cons 73 0)
          (cons 74 0)
          (cons 280 1)
         )
         (list
          (cons 0 "ATTDEF")
          (cons 100 "AcDbEntity")
          (cons 67 0)
          (cons 8 "0")
          (cons 100 "AcDbText")
          (list 10 -0.63095238 -9.96428571 0.00000000)
          (cons 40  0.50000000)
          (cons 1 "1.0")
          (cons 50  0.00000000)
          (cons 41  1.00000000)
          (cons 51  0.00000000)
          (cons 7 "Standard")
          (cons 71 0)
          (cons 72 4)
          (list 11 0.00000000 -9.71428571 0.00000000)
          (list 210 0.00000000 0.00000000 1.00000000)
          (cons 100 "AcDbAttributeDefinition")
          (cons 280 0)
          (cons 3 "Ditch Width")
          (cons 2 "CUTDITCHWIDTH")
          (cons 70 1)
          (cons 73 0)
          (cons 74 0)
          (cons 280 1)
         )
         (list (cons 0 "ENDBLK"))
        )
       )
       ((= (strcase BLKNAME) "RTESTTRAINSECTION")
        (list
         (list
          (cons 0 "BLOCK")
          (cons 2 "RTESTTRAINSECTION")
          (cons 70  0)
          (cons 4 "")
          (list 10 0.00000000 0.00000000 0.00000000)
         )
         (list
          (cons 0 "LWPOLYLINE")
          (cons 100 "AcDbEntity")
          (cons 67 0)
          (cons 8 "0")
          (cons 6 "DASHED")
          (cons 100 "AcDbPolyline")
          (cons 90 11)
          (cons 70 0)
          (cons 43  0.00000000)
          (cons 38  0.00000000)
          (cons 39  0.00000000)
          (list 10 0.98500000 0.37264481)
          (cons 40  0.00000000)
          (cons 41  0.00000000)
          (cons 42  0.00000000)
          (cons 91 0)
          (list 10 1.19260839 0.37264481)
          (cons 40  0.00000000)
          (cons 41  0.00000000)
          (cons 42  0.36674153)
          (cons 91 0)
          (list 10 1.38990017 0.53984304)
          (cons 40  0.00000000)
          (cons 41  0.00000000)
          (cons 42  0.00000000)
          (cons 91 0)
          (list 10 1.53397065 1.40637923)
          (cons 40  0.00000000)
          (cons 41  0.00000000)
          (cons 42  0.03126153)
          (cons 91 0)
          (list 10 1.55309759 1.59278654)
          (cons 40  0.00000000)
          (cons 41  0.00000000)
          (cons 42  0.00000000)
          (cons 91 0)
          (list 10 1.59200204 2.57105401)
          (cons 40  0.00000000)
          (cons 41  0.00000000)
          (cons 42  0.00000000)
          (cons 91 0)
          (list 10 1.59200204 2.73424074)
          (cons 40  0.00000000)
          (cons 41  0.00000000)
          (cons 42  0.22029118)
          (cons 91 0)
          (list 10 1.53903384 2.84862968)
          (cons 40  0.00000000)
          (cons 41  0.00000000)
          (cons 42  0.00000000)
          (cons 91 0)
          (list 10 1.28083281 3.06765181)
          (cons 40  0.00000000)
          (cons 41  0.00000000)
          (cons 42  0.17771548)
          (cons 91 0)
          (list 10 0.12000000 3.49366052)
          (cons 40  0.00000000)
          (cons 41  0.00000000)
          (cons 42  0.00000000)
          (cons 91 0)
          (list 10 0.00000000 3.49366052)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 6 "DASHED2")
          (cons 100 "AcDbLine")
          (list 10 0.11999839 3.59366052 0.00000000)
          (list 11 0.00000000 3.59366052 0.00000000)
          (list 210 0.00000000 0.00000000 1.00000000)
         )
         (list
          (cons 0 "ARC")
          (cons 100 "AcDbEntity")
          (cons 67 0)
          (cons 8 "0")
          (cons 6 "DASHED2")
          (cons 100 "AcDbCircle")
          (list 10 1.19260839 0.57264481 0.00000000)
          (cons 40  0.30000000)
          (list 210 0.00000000 0.00000000 1.00000000)
          (cons 100 "AcDbArc")
          (cons 50  4.71238898)
          (cons 51  6.11843213)
         )
         (list
          (cons 0 "ARC")
          (cons 100 "AcDbEntity")
          (cons 67 0)
          (cons 8 "0")
          (cons 6 "DASHED2")
          (cons 100 "AcDbCircle")
          (list 10 1.44200204 2.73424074 0.00000000)
          (cons 40  0.25000000)
          (list 210 0.00000000 0.00000000 1.00000000)
          (cons 100 "AcDbArc")
          (cons 50  0.00000000)
          (cons 51  0.86731211)
         )
         (list
          (cons 0 "ARC")
          (cons 100 "AcDbEntity")
          (cons 67 0)
          (cons 8 "0")
          (cons 6 "DASHED2")
          (cons 100 "AcDbCircle")
          (list 10 0.12005876 1.69923732 0.00000000)
          (cons 40  1.89442321)
          (list 210 0.00000000 0.00000000 1.00000000)
          (cons 100 "AcDbArc")
          (cons 50  1.39629614)
          (cons 51  1.57082819)
         )
         (list (cons 0 "ENDBLK"))
        )
       )
       ((= (strcase BLKNAME) "RTRAINSECTION")
        (list
         (list
          (cons 0 "BLOCK")
          (cons 2 "RTRAINSECTION")
          (cons 70  0)
          (cons 4 "")
          (list 10 0.00000000 0.00000000 0.00000000)
         )
         (list
          (cons 0 "LWPOLYLINE")
          (cons 100 "AcDbEntity")
          (cons 67 0)
          (cons 8 "0")
          (cons 6 "DASHED")
          (cons 100 "AcDbPolyline")
          (cons 90 11)
          (cons 70 0)
          (cons 43  0.00000000)
          (cons 38  0.00000000)
          (cons 39  0.00000000)
          (list 10 0.98500000 0.37264481)
          (cons 40  0.00000000)
          (cons 41  0.00000000)
          (cons 42  0.00000000)
          (cons 91 0)
          (list 10 1.19260839 0.37264481)
          (cons 40  0.00000000)
          (cons 41  0.00000000)
          (cons 42  0.36674153)
          (cons 91 0)
          (list 10 1.38990017 0.53984304)
          (cons 40  0.00000000)
          (cons 41  0.00000000)
          (cons 42  0.00000000)
          (cons 91 0)
          (list 10 1.53397065 1.40637923)
          (cons 40  0.00000000)
          (cons 41  0.00000000)
          (cons 42  0.03126153)
          (cons 91 0)
          (list 10 1.55309759 1.59278654)
          (cons 40  0.00000000)
          (cons 41  0.00000000)
          (cons 42  0.00000000)
          (cons 91 0)
          (list 10 1.59200204 2.57105401)
          (cons 40  0.00000000)
          (cons 41  0.00000000)
          (cons 42  0.00000000)
          (cons 91 0)
          (list 10 1.59200204 2.73424074)
          (cons 40  0.00000000)
          (cons 41  0.00000000)
          (cons 42  0.22029118)
          (cons 91 0)
          (list 10 1.53903384 2.84862968)
          (cons 40  0.00000000)
          (cons 41  0.00000000)
          (cons 42  0.00000000)
          (cons 91 0)
          (list 10 1.28083281 3.06765181)
          (cons 40  0.00000000)
          (cons 41  0.00000000)
          (cons 42  0.17771548)
          (cons 91 0)
          (list 10 0.12000000 3.49366052)
          (cons 40  0.00000000)
          (cons 41  0.00000000)
          (cons 42  0.00000000)
          (cons 91 0)
          (list 10 0.00000000 3.49366052)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 6 "DASHED2")
          (cons 100 "AcDbLine")
          (list 10 0.11999839 3.59366052 0.00000000)
          (list 11 0.00000000 3.59366052 0.00000000)
          (list 210 0.00000000 0.00000000 1.00000000)
         )
         (list
          (cons 0 "ARC")
          (cons 100 "AcDbEntity")
          (cons 67 0)
          (cons 8 "0")
          (cons 6 "DASHED2")
          (cons 100 "AcDbCircle")
          (list 10 1.19260839 0.57264481 0.00000000)
          (cons 40  0.30000000)
          (list 210 0.00000000 0.00000000 1.00000000)
          (cons 100 "AcDbArc")
          (cons 50  4.71238898)
          (cons 51  6.11843213)
         )
         (list
          (cons 0 "ARC")
          (cons 100 "AcDbEntity")
          (cons 67 0)
          (cons 8 "0")
          (cons 6 "DASHED2")
          (cons 100 "AcDbCircle")
          (list 10 1.44200204 2.73424074 0.00000000)
          (cons 40  0.25000000)
          (list 210 0.00000000 0.00000000 1.00000000)
          (cons 100 "AcDbArc")
          (cons 50  0.00000000)
          (cons 51  0.86731211)
         )
         (list
          (cons 0 "ARC")
          (cons 100 "AcDbEntity")
          (cons 67 0)
          (cons 8 "0")
          (cons 6 "DASHED2")
          (cons 100 "AcDbCircle")
          (list 10 0.12005876 1.69923732 0.00000000)
          (cons 40  1.89442321)
          (list 210 0.00000000 0.00000000 1.00000000)
          (cons 100 "AcDbArc")
          (cons 50  1.39629614)
          (cons 51  1.57082819)
         )
         (list (cons 0 "ENDBLK"))
        )
       )
       ((= (strcase BLKNAME) "SECT-REF")
        (list
         (list
          (cons 0 "BLOCK")
          (cons 2 "SECT-REF")
          (cons 70  2)
          (cons 4 "")
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  0.05000000)
          (list 210 0.00000000 0.00000000 1.00000000)
         )
         (list
          (cons 0 "LWPOLYLINE")
          (cons 100 "AcDbEntity")
          (cons 67 0)
          (cons 8 "0")
          (cons 100 "AcDbPolyline")
          (cons 90 2)
          (cons 70 0)
          (cons 43  0.05000000)
          (cons 38  0.00000000)
          (cons 39  0.00000000)
          (list 10 0.00000000 0.02500000)
          (cons 40  0.05000000)
          (cons 41  0.05000000)
          (cons 42  0.41421356)
          (cons 91 0)
          (list 10 -0.02500000 0.00000000)
          (cons 40  0.05000000)
          (cons 41  0.05000000)
          (cons 42  1.00000000)
          (cons 91 0)
          (list 210 0.00000000 0.00000000 1.00000000)
         )
         (list
          (cons 0 "LWPOLYLINE")
          (cons 100 "AcDbEntity")
          (cons 67 0)
          (cons 8 "0")
          (cons 100 "AcDbPolyline")
          (cons 90 2)
          (cons 70 0)
          (cons 43  0.05000000)
          (cons 38  0.00000000)
          (cons 39  0.00000000)
          (list 10 0.00000000 -0.02500000)
          (cons 40  0.05000000)
          (cons 41  0.05000000)
          (cons 42  0.41421356)
          (cons 91 0)
          (list 10 0.02500000 0.00000000)
          (cons 40  0.05000000)
          (cons 41  0.05000000)
          (cons 42  1.00000000)
          (cons 91 0)
          (list 210 0.00000000 0.00000000 1.00000000)
         )
         (list
          (cons 0 "LINE")
          (cons 100 "AcDbEntity")
          (cons 67 0)
          (cons 8 "0")
          (cons 100 "AcDbLine")
          (list 10 -0.10000000 0.00000000 0.00000000)
          (list 11 0.10000000 0.00000000 0.00000000)
          (list 210 0.00000000 0.00000000 1.00000000)
         )
         (list
          (cons 0 "LINE")
          (cons 100 "AcDbEntity")
          (cons 67 0)
          (cons 8 "0")
          (cons 100 "AcDbLine")
          (list 10 0.00000000 0.10000000 0.00000000)
          (list 11 0.00000000 -0.10000000 0.00000000)
          (list 210 0.00000000 0.00000000 1.00000000)
         )
         (list
          (cons 0 "TEXT")
          (cons 100 "AcDbEntity")
          (cons 67 0)
          (cons 8 "0")
          (cons 100 "AcDbText")
          (list 10 0.12500000 0.05000000 0.00000000)
          (cons 40  0.05000000)
          (cons 1 "N:")
          (cons 50  0.00000000)
          (cons 41  0.80000000)
          (cons 51  0.00000000)
          (cons 7 "Standard")
          (cons 71 0)
          (cons 72 0)
          (list 11 0.12500000 0.07500000 0.00000000)
          (list 210 0.00000000 0.00000000 1.00000000)
          (cons 100 "AcDbText")
          (cons 73 2)
         )
         (list
          (cons 0 "TEXT")
          (cons 100 "AcDbEntity")
          (cons 67 0)
          (cons 8 "0")
          (cons 100 "AcDbText")
          (list 10 0.12500000 -0.02500000 0.00000000)
          (cons 40  0.05000000)
          (cons 1 "E:")
          (cons 50  0.00000000)
          (cons 41  0.80000000)
          (cons 51  0.00000000)
          (cons 7 "Standard")
          (cons 71 0)
          (cons 72 0)
          (list 11 0.12500000 0.00000000 0.00000000)
          (list 210 0.00000000 0.00000000 1.00000000)
          (cons 100 "AcDbText")
          (cons 73 2)
         )
         (list
          (cons 0 "TEXT")
          (cons 100 "AcDbEntity")
          (cons 67 0)
          (cons 8 "0")
          (cons 100 "AcDbText")
          (list 10 0.12500000 -0.10000000 0.00000000)
          (cons 40  0.05000000)
          (cons 1 "Z:")
          (cons 50  0.00000000)
          (cons 41  0.80000000)
          (cons 51  0.00000000)
          (cons 7 "Standard")
          (cons 71 0)
          (cons 72 0)
          (list 11 0.12500000 -0.07500000 0.00000000)
          (list 210 0.00000000 0.00000000 1.00000000)
          (cons 100 "AcDbText")
          (cons 73 2)
         )
         (list
          (cons 0 "ATTDEF")
          (cons 100 "AcDbEntity")
          (cons 67 0)
          (cons 8 "0")
          (cons 100 "AcDbText")
          (list 10 0.20000000 0.05000000 0.00000000)
          (cons 40  0.05000000)
          (cons 1 "")
          (cons 50  0.00000000)
          (cons 41  0.80000000)
          (cons 51  0.00000000)
          (cons 7 "Standard")
          (cons 71 0)
          (cons 72 0)
          (list 11 0.20000000 0.07500000 0.00000000)
          (list 210 0.00000000 0.00000000 1.00000000)
          (cons 100 "AcDbAttributeDefinition")
          (cons 280 0)
          (cons 3 "Northing")
          (cons 2 "N")
          (cons 70 0)
          (cons 73 0)
          (cons 74 2)
          (cons 280 0)
         )
         (list
          (cons 0 "ATTDEF")
          (cons 100 "AcDbEntity")
          (cons 67 0)
          (cons 8 "0")
          (cons 100 "AcDbText")
          (list 10 0.20000000 -0.02500000 0.00000000)
          (cons 40  0.05000000)
          (cons 1 "")
          (cons 50  0.00000000)
          (cons 41  0.80000000)
          (cons 51  0.00000000)
          (cons 7 "Standard")
          (cons 71 0)
          (cons 72 0)
          (list 11 0.20000000 0.00000000 0.00000000)
          (list 210 0.00000000 0.00000000 1.00000000)
          (cons 100 "AcDbAttributeDefinition")
          (cons 280 0)
          (cons 3 "Easting")
          (cons 2 "E")
          (cons 70 0)
          (cons 73 0)
          (cons 74 2)
          (cons 280 0)
         )
         (list
          (cons 0 "ATTDEF")
          (cons 100 "AcDbEntity")
          (cons 67 0)
          (cons 8 "0")
          (cons 100 "AcDbText")
          (list 10 0.20000000 -0.10000000 0.00000000)
          (cons 40  0.05000000)
          (cons 1 "")
          (cons 50  0.00000000)
          (cons 41  0.80000000)
          (cons 51  0.00000000)
          (cons 7 "Standard")
          (cons 71 0)
          (cons 72 0)
          (list 11 0.20000000 -0.07500000 0.00000000)
          (list 210 0.00000000 0.00000000 1.00000000)
          (cons 100 "AcDbAttributeDefinition")
          (cons 280 0)
          (cons 3 "Elevation")
          (cons 2 "Z")
          (cons 70 0)
          (cons 73 0)
          (cons 74 2)
          (cons 280 0)
         )
         (list
          (cons 0 "CIRCLE")
          (cons 100 "AcDbEntity")
          (cons 67 0)
          (cons 8 "0")
          (cons 6 "DASHED2")
          (cons 100 "AcDbCircle")
          (list 10 0.00000000 0.00000000 0.00000000)
          (cons 40  0.10000000)
          (list 210 0.00000000 0.00000000 1.00000000)
         )
         (list (cons 0 "ENDBLK"))
        )
       )
       ((= (strcase BLKNAME) "SPOTELEVATION")
        (list
         (list
          (cons 0 "BLOCK")
          (cons 2 "spotelevation")
          (cons 70  2)
          (list 10 0.00000000 0.00000000 0.00000000)
         )
         (list
          (cons 0 "ATTDEF")
          (cons 100 "AcDbEntity")
          (cons 67 0)
          (cons 8 "0")
          (cons 100 "AcDbText")
          (list 10 0.00000000 1.20000000 0.00000000)
          (cons 40  0.75000000)
          (cons 1 "")
          (cons 50  0.00000000)
          (cons 41  1.00000000)
          (cons 51  0.00000000)
          (cons 7 "Standard")
          (cons 71 0)
          (cons 72 4)
          (list 11 0.00000000 1.20000000 0.00000000)
          (list 210 0.00000000 0.00000000 1.00000000)
          (cons 100 "AcDbAttributeDefinition")
          (cons 280 0)
          (cons 3 "Elevation:")
          (cons 2 "ELEV")
          (cons 70 0)
          (cons 73 0)
          (cons 74 0)
          (cons 280 0)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list (cons 0 "ENDBLK"))
        )
       )
       ((= (strcase BLKNAME) "SPOTELEVATION2")
        (list
         (list
          (cons 0 "BLOCK")
          (cons 2 "spotelevation2")
          (cons 70  2)
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 0.00207694 -1.20000180 0.00000000)
          (cons 40  0.75000000)
          (cons 1 "")
          (cons 50  6.28145452)
          (cons 41  1.00000000)
          (cons 51  0.00000000)
          (cons 7 "Standard")
          (cons 71 0)
          (cons 72 4)
          (list 11 0.00207694 -1.20000180 0.00000000)
          (list 210 0.00000000 0.00000000 1.00000000)
          (cons 100 "AcDbAttributeDefinition")
          (cons 280 0)
          (cons 3 "Elevation:")
          (cons 2 "ELEV")
          (cons 70 0)
          (cons 73 0)
          (cons 74 0)
          (cons 280 0)
         )
         (list (cons 0 "ENDBLK"))
        )
       )
       ((= (strcase BLKNAME) "STALBL")
        (list
         (list
          (cons 0 "BLOCK")
          (cons 2 "STALBL")
          (cons 70  2)
          (list 10 0.00000000 0.00000000 0.00000000)
         )
         (list
          (cons 0 "ATTDEF")
          (cons 100 "AcDbEntity")
          (cons 67 0)
          (cons 8 "0")
          (cons 100 "AcDbText")
          (list 10 -6.92857143 -1.00000000 0.00000000)
          (cons 40  2.00000000)
          (cons 1 "100")
          (cons 50  0.00000000)
          (cons 41  1.00000000)
          (cons 51  0.00000000)
          (cons 7 "Standard")
          (cons 71 0)
          (cons 72 2)
          (list 11 -1.50000000 0.00000000 0.00000000)
          (list 210 0.00000000 0.00000000 1.00000000)
          (cons 100 "AcDbAttributeDefinition")
          (cons 280 0)
          (cons 3 "STAH")
          (cons 2 "STAH")
          (cons 70 0)
          (cons 73 0)
          (cons 74 2)
          (cons 280 0)
         )
         (list
          (cons 0 "ATTDEF")
          (cons 100 "AcDbEntity")
          (cons 67 0)
          (cons 8 "0")
          (cons 100 "AcDbText")
          (list 10 1.50000000 -1.00000000 0.00000000)
          (cons 40  2.00000000)
          (cons 1 "000.000")
          (cons 50  0.00000000)
          (cons 41  1.00000000)
          (cons 51  0.00000000)
          (cons 7 "Standard")
          (cons 71 0)
          (cons 72 0)
          (list 11 1.50000000 0.00000000 0.00000000)
          (list 210 0.00000000 0.00000000 1.00000000)
          (cons 100 "AcDbAttributeDefinition")
          (cons 280 0)
          (cons 3 "STAL")
          (cons 2 "STAL")
          (cons 70 0)
          (cons 73 0)
          (cons 74 2)
          (cons 280 0)
         )
         (list
          (cons 0 "TEXT")
          (cons 100 "AcDbEntity")
          (cons 67 0)
          (cons 8 "0")
          (cons 100 "AcDbText")
          (list 10 -1.23809524 -0.85714286 0.00000000)
          (cons 40  2.00000000)
          (cons 1 "+")
          (cons 50  0.00000000)
          (cons 41  1.00000000)
          (cons 51  0.00000000)
          (cons 7 "Standard")
          (cons 71 0)
          (cons 72 4)
          (list 11 0.00000000 0.00000000 0.00000000)
          (list 210 0.00000000 0.00000000 1.00000000)
          (cons 100 "AcDbText")
          (cons 73 0)
         )
         (list (cons 0 "ENDBLK"))
        )
       )
       ((= (strcase BLKNAME) "STANODELEFT")
        (list
         (list
          (cons 0 "BLOCK")
          (cons 2 "STANODELEFT")
          (cons 70  2)
          (list 10 0.00000000 0.00000000 0.00000000)
         )
         (list
          (cons 0 "LINE")
          (cons 100 "AcDbEntity")
          (cons 67 0)
          (cons 8 "0")
          (cons 100 "AcDbLine")
          (list 10 0.00000000 0.00000000 0.00000000)
          (list 11 0.00000000 40.00000000 0.00000000)
          (list 210 0.00000000 0.00000000 1.00000000)
         )
         (list
          (cons 0 "ATTDEF")
          (cons 100 "AcDbEntity")
          (cons 67 0)
          (cons 8 "0")
          (cons 100 "AcDbText")
          (list 10 0.66666667 40.00000000 0.00000000)
          (cons 40  2.00000000)
          (cons 1 "TS 100+000.000")
          (cons 50  4.71238898)
          (cons 41  1.00000000)
          (cons 51  0.00000000)
          (cons 7 "Standard")
          (cons 71 0)
          (cons 72 0)
          (list 11 0.00000000 40.00000000 0.00000000)
          (list 210 0.00000000 0.00000000 1.00000000)
          (cons 100 "AcDbAttributeDefinition")
          (cons 280 0)
          (cons 3 "Node text")
          (cons 2 "NODE")
          (cons 70 0)
          (cons 73 0)
          (cons 74 1)
          (cons 280 0)
         )
         (list (cons 0 "ENDBLK"))
        )
       )
       ((= (strcase BLKNAME) "STANODERIGHT")
        (list
         (list
          (cons 0 "BLOCK")
          (cons 2 "STANODERIGHT")
          (cons 70  2)
          (list 10 0.00000000 0.00000000 0.00000000)
         )
         (list
          (cons 0 "LINE")
          (cons 100 "AcDbEntity")
          (cons 67 0)
          (cons 8 "0")
          (cons 100 "AcDbLine")
          (list 10 0.00000000 0.00000000 0.00000000)
          (list 11 0.00000000 -40.00000000 0.00000000)
          (list 210 0.00000000 0.00000000 1.00000000)
         )
         (list
          (cons 0 "ATTDEF")
          (cons 100 "AcDbEntity")
          (cons 67 0)
          (cons 8 "0")
          (cons 100 "AcDbText")
          (list 10 0.66666667 -14.28571429 0.00000000)
          (cons 40  2.00000000)
          (cons 1 "TS 100+000.000")
          (cons 50  4.71238898)
          (cons 41  1.00000000)
          (cons 51  0.00000000)
          (cons 7 "Standard")
          (cons 71 0)
          (cons 72 2)
          (list 11 0.00000000 -40.00000000 0.00000000)
          (list 210 0.00000000 0.00000000 1.00000000)
          (cons 100 "AcDbAttributeDefinition")
          (cons 280 0)
          (cons 3 "Node text")
          (cons 2 "NODE")
          (cons 70 0)
          (cons 73 0)
          (cons 74 1)
          (cons 280 0)
         )
         (list (cons 0 "ENDBLK"))
        )
       )
       ((= (strcase BLKNAME) "STATICK")
        (list
         (list
          (cons 0 "BLOCK")
          (cons 2 "STATICK")
          (cons 70  0)
          (list 10 0.00000000 0.00000000 0.00000000)
         )
         (list
          (cons 0 "LINE")
          (cons 100 "AcDbEntity")
          (cons 67 0)
          (cons 8 "0")
          (cons 100 "AcDbLine")
          (list 10 0.00000000 -0.75000000 0.00000000)
          (list 11 0.00000000 0.75000000 0.00000000)
          (list 210 0.00000000 0.00000000 1.00000000)
         )
         (list (cons 0 "ENDBLK"))
        )
       )
       ((= (strcase BLKNAME) "SUPER")
        (list
         (list
          (cons 0 "BLOCK")
          (cons 2 "super")
          (cons 70  2)
          (list 10 0.00000000 0.00000000 0.00000000)
         )
         (list
          (cons 0 "ATTDEF")
          (cons 100 "AcDbEntity")
          (cons 67 0)
          (cons 8 "0")
          (cons 100 "AcDbText")
          (list 10 0.00000000 -1.20000000 0.00000000)
          (cons 40  0.75000000)
          (cons 1 "")
          (cons 50  0.00000000)
          (cons 41  1.00000000)
          (cons 51  0.00000000)
          (cons 7 "Standard")
          (cons 71 0)
          (cons 72 4)
          (list 11 0.00000000 -1.20000000 0.00000000)
          (list 210 0.00000000 0.00000000 1.00000000)
          (cons 100 "AcDbAttributeDefinition")
          (cons 280 0)
          (cons 3 "Left superlevation")
          (cons 2 "LEFT")
          (cons 70 0)
          (cons 73 0)
          (cons 74 0)
          (cons 280 0)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 0.00000000 1.20000000 0.00000000)
          (cons 40  0.75000000)
          (cons 1 "")
          (cons 50  0.00000000)
          (cons 41  1.00000000)
          (cons 51  0.00000000)
          (cons 7 "Standard")
          (cons 71 0)
          (cons 72 4)
          (list 11 0.00000000 1.20000000 0.00000000)
          (list 210 0.00000000 0.00000000 1.00000000)
          (cons 100 "AcDbAttributeDefinition")
          (cons 280 0)
          (cons 3 "Right superlevation")
          (cons 2 "RIGHT")
          (cons 70 0)
          (cons 73 0)
          (cons 74 0)
          (cons 280 0)
         )
         (list (cons 0 "ENDBLK"))
        )
       )
       ((= (strcase BLKNAME) "SURVEYSPOT")
        (list
         (list
          (cons 0 "BLOCK")
          (cons 2 "surveyspot")
          (cons 70  2)
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 1.00000000 1.21428571 0.00000000)
          (cons 40  1.00000000)
          (cons 1 "")
          (cons 50  0.00000000)
          (cons 41  0.75000000)
          (cons 51  0.00000000)
          (cons 7 "Standard")
          (cons 71 0)
          (cons 72 0)
          (list 11 1.00000000 1.71428571 0.00000000)
          (list 210 0.00000000 0.00000000 1.00000000)
          (cons 100 "AcDbAttributeDefinition")
          (cons 280 0)
          (cons 3 "Point Number")
          (cons 2 "PNTNO")
          (cons 70 0)
          (cons 73 0)
          (cons 74 2)
          (cons 280 0)
         )
         (list
          (cons 0 "ATTDEF")
          (cons 100 "AcDbEntity")
          (cons 67 0)
          (cons 8 "0")
          (cons 100 "AcDbText")
          (list 10 1.00000000 -0.50000000 0.00000000)
          (cons 40  1.00000000)
          (cons 1 "")
          (cons 50  0.00000000)
          (cons 41  0.75000000)
          (cons 51  0.00000000)
          (cons 7 "Standard")
          (cons 71 0)
          (cons 72 0)
          (list 11 1.00000000 0.00000000 0.00000000)
          (list 210 0.00000000 0.00000000 1.00000000)
          (cons 100 "AcDbAttributeDefinition")
          (cons 280 0)
          (cons 3 "ELEVATION")
          (cons 2 "ELEV")
          (cons 70 0)
          (cons 73 0)
          (cons 74 2)
          (cons 280 0)
         )
         (list
          (cons 0 "ATTDEF")
          (cons 100 "AcDbEntity")
          (cons 67 0)
          (cons 8 "0")
          (cons 100 "AcDbText")
          (list 10 1.00000000 -2.21428571 0.00000000)
          (cons 40  1.00000000)
          (cons 1 "")
          (cons 50  0.00000000)
          (cons 41  0.75000000)
          (cons 51  0.00000000)
          (cons 7 "Standard")
          (cons 71 0)
          (cons 72 0)
          (list 11 1.00000000 -1.71428571 0.00000000)
          (list 210 0.00000000 0.00000000 1.00000000)
          (cons 100 "AcDbAttributeDefinition")
          (cons 280 0)
          (cons 3 "Description")
          (cons 2 "DESC")
          (cons 70 0)
          (cons 73 0)
          (cons 74 2)
          (cons 280 0)
         )
         (list (cons 0 "ENDBLK"))
        )
       )
       ((= (strcase BLKNAME) "TESTTRAINSECTION")
        (list
         (list
          (cons 0 "BLOCK")
          (cons 2 "TESTTRAINSECTION")
          (cons 70  0)
          (cons 4 "")
          (list 10 0.00000000 0.00000000 0.00000000)
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.24400000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.24400000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.98500000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.98500000 0.37264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.19260839 0.37264481 0.00000000)
          (cons 40  0.00000000)
          (cons 41  0.00000000)
          (cons 42  0.36674153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.38990017 0.53984304 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.53397065 1.40637923 0.00000000)
          (cons 40  0.00000000)
          (cons 41  0.00000000)
          (cons 42  0.03126153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.55309759 1.59278654 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.59200204 2.57105401 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.59200204 2.73424074 0.00000000)
          (cons 40  0.00000000)
          (cons 41  0.00000000)
          (cons 42  0.22029118)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.53903384 2.84862968 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.28083281 3.06765181 0.00000000)
          (cons 40  0.00000000)
          (cons 41  0.00000000)
          (cons 42  0.17771548)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.12000000 3.49366052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.49366052 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
         )
         (list
          (cons 0 "LINE")
          (cons 100 "AcDbEntity")
          (cons 67 0)
          (cons 8 "0")
          (cons 62 1)
          (cons 6 "CENTER")
          (cons 100 "AcDbLine")
          (list 10 -1.04663306 0.00000000 0.00000000)
          (list 11 1.00417210 0.00000000 0.00000000)
          (list 210 0.00000000 0.00000000 1.00000000)
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.70500000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.70500000 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.13419281 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.19640989 0.63050138 0.00000000)
          (cons 40  0.00000000)
          (cons 41  0.00000000)
          (cons 42  0.23680896)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.20043142 0.63407757 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.25847950 0.78241446 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.26469703 0.84193015 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.31417907 1.31558441 0.00000000)
          (cons 40  0.00000000)
          (cons 41  0.00000000)
          (cons 42  0.04350349)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.32014277 1.66351168 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.24431542 2.74789338 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.28681165 2.75086501 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.27966113 2.85312219 0.00000000)
          (cons 40  0.00000000)
          (cons 41  0.00000000)
          (cons 42  0.22584867)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.21626311 2.96539115 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.10681069 3.04229668 0.00000000)
          (cons 40  0.00000000)
          (cons 41  0.00000000)
          (cons 42  0.15433180)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.39226450 0.00000000)
          (cons 40  0.00000000)
          (cons 41  0.00000000)
          (cons 42  0.15433180)
          (cons 91 0)
          (cons 70 0)
          (cons 50  0.00000000)
         )
         (list
          (cons 0 "SEQEND")
          (cons 100 "AcDbEntity")
          (cons 67 0)
          (cons 8 "0")
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.24400000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.24400000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.98500000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.98500000 0.37264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.19260839 0.37264481 0.00000000)
          (cons 40  0.00000000)
          (cons 41  0.00000000)
          (cons 42  -0.36674153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.38990017 0.53984304 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.53397065 1.40637923 0.00000000)
          (cons 40  0.00000000)
          (cons 41  0.00000000)
          (cons 42  -0.03126153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.55309759 1.59278654 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.59200204 2.57105401 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.59200204 2.73424074 0.00000000)
          (cons 40  0.00000000)
          (cons 41  0.00000000)
          (cons 42  -0.22029118)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.53903384 2.84862968 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.28083281 3.06765181 0.00000000)
          (cons 40  0.00000000)
          (cons 41  0.00000000)
          (cons 42  -0.17771548)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.12000000 3.49366052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.49366052 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.70500000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.70500000 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.13419281 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.19640989 0.63050138 0.00000000)
          (cons 40  0.00000000)
          (cons 41  0.00000000)
          (cons 42  -0.23680896)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.20043142 0.63407757 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.25847950 0.78241446 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.26469703 0.84193015 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.31417907 1.31558441 0.00000000)
          (cons 40  0.00000000)
          (cons 41  0.00000000)
          (cons 42  -0.04350349)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.32014277 1.66351168 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.24431542 2.74789338 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.28681165 2.75086501 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.27966113 2.85312219 0.00000000)
          (cons 40  0.00000000)
          (cons 41  0.00000000)
          (cons 42  -0.22584867)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.21626311 2.96539115 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.10681069 3.04229668 0.00000000)
          (cons 40  0.00000000)
          (cons 41  0.00000000)
          (cons 42  -0.15433180)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.39226450 0.00000000)
          (cons 40  0.00000000)
          (cons 41  0.00000000)
          (cons 42  -0.15433180)
          (cons 91 0)
          (cons 70 0)
          (cons 50  0.00000000)
         )
         (list
          (cons 0 "SEQEND")
          (cons 100 "AcDbEntity")
          (cons 67 0)
          (cons 8 "0")
         )
         (list
          (cons 0 "LINE")
          (cons 100 "AcDbEntity")
          (cons 67 0)
          (cons 8 "0")
          (cons 62 1)
          (cons 6 "CENTER")
          (cons 100 "AcDbLine")
          (list 10 0.00000000 -0.48642537 0.00000000)
          (list 11 0.00000000 4.05187199 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.91229985 -0.33897276 0.00000000)
          (list 11 -0.91229985 -0.35078869 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90267615 -0.35078869 0.00000000)
          (list 11 -0.90267615 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88342874 -0.35078869 0.00000000)
          (list 11 -0.88342874 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.60710504 -0.33897276 0.00000000)
          (list 11 -0.60710504 -0.35078869 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.63597615 -0.35078869 0.00000000)
          (list 11 -0.63597615 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.61672874 -0.35078869 0.00000000)
          (list 11 -0.61672874 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.64559985 -0.35078869 0.00000000)
          (list 11 -0.64559985 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.87380504 -0.35078869 0.00000000)
          (list 11 -0.87380504 -0.33897276 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.87861689 -0.34491297 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 -0.90748800 -0.34491297 0.00000000)
          (cons 40  0.00759460)
          (list 210 0.00000000 0.00000000 1.00000000)
          (cons 100 "AcDbArc")
          (cons 50  4.02620608)
          (cons 51  5.39857188)
         )
         (list
          (cons 0 "LINE")
          (cons 100 "AcDbEntity")
          (cons 67 0)
          (cons 8 "0")
          (cons 62 1)
          (cons 6 "Continuous")
          (cons 100 "AcDbLine")
          (list 10 -0.87861689 -0.35250778 0.00000000)
          (list 11 -0.90748800 -0.35250778 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89305244 -0.32470996 0.00000000)
          (cons 40  0.02779776)
          (list 210 0.00000000 0.00000000 1.00000000)
          (cons 100 "AcDbArc")
          (cons 50  4.35886680)
          (cons 51  5.06591116)
         )
         (list
          (cons 0 "ARC")
          (cons 100 "AcDbEntity")
          (cons 67 0)
          (cons 8 "0")
          (cons 62 1)
          (cons 100 "AcDbCircle")
          (list 10 -0.62635244 -0.32470996 0.00000000)
          (cons 40  0.02779776)
          (list 210 0.00000000 0.00000000 1.00000000)
          (cons 100 "AcDbArc")
          (cons 50  4.35886680)
          (cons 51  5.06591116)
         )
         (list
          (cons 0 "LINE")
          (cons 100 "AcDbEntity")
          (cons 67 0)
          (cons 8 "0")
          (cons 62 1)
          (cons 6 "Continuous")
          (cons 100 "AcDbLine")
          (list 10 -0.64078800 -0.35250778 0.00000000)
          (list 11 -0.61191689 -0.35250778 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.64078800 -0.34491297 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 -0.61191689 -0.34491297 0.00000000)
          (cons 40  0.00759460)
          (list 210 0.00000000 0.00000000 1.00000000)
          (cons 100 "AcDbArc")
          (cons 50  4.02620608)
          (cons 51  5.39857188)
         )
         (list
          (cons 0 "LINE")
          (cons 100 "AcDbEntity")
          (cons 67 0)
          (cons 8 "0")
          (cons 62 1)
          (cons 6 "Continuous")
          (cons 100 "AcDbLine")
          (list 10 -0.69431261 -0.21482876 0.00000000)
          (list 11 -0.75970244 -0.21482876 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.80667000 -0.18806435 0.00000000)
          (list 11 -0.71273486 -0.18806435 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.80871883 -0.18501635 0.00000000)
          (list 11 -0.71068606 -0.18501635 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.82923307 -0.16502980 0.00000000)
          (list 11 -0.69031645 -0.17197566 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.75970244 -0.21673376 0.00000000)
          (list 11 -0.56723394 -0.21673376 0.00000000)
          (list 210 0.00000000 0.00000000 1.00000000)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 -0.87555244 -0.21992629 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.54951744 -0.21992629 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 -0.76845357 -0.12956735 0.00000000)
          (cons 40  0.00000000)
          (cons 41  0.00000000)
          (cons 42  0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.76335470 -0.05359212 0.00000000)
          (cons 40  0.00000000)
          (cons 41  0.00000000)
          (cons 42  0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.77685274 -0.03613117 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78626869 -0.03327115 0.00000000)
          (cons 40  0.00000000)
          (cons 41  0.00000000)
          (cons 42  -0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78739919 -0.03162037 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78582129 -0.01061412 0.00000000)
          (cons 40  0.00000000)
          (cons 41  0.00000000)
          (cons 42  -0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.77953528 -0.00236373 0.00000000)
          (cons 40  0.00000000)
          (cons 41  0.00000000)
          (cons 42  -0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.76717895 -0.00013950 0.00000000)
          (cons 40  0.00000000)
          (cons 41  0.00000000)
          (cons 42  -0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.75129895 -0.00043630 0.00000000)
          (cons 40  0.00000000)
          (cons 41  0.00000000)
          (cons 42  -0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.73546856 -0.00172502 0.00000000)
          (cons 40  0.00000000)
          (cons 41  0.00000000)
          (cons 42  -0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.72339572 -0.00517070 0.00000000)
          (cons 40  0.00000000)
          (cons 41  0.00000000)
          (cons 42  -0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.71796404 -0.01400698 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.71848940 -0.03506586 0.00000000)
          (cons 40  0.00000000)
          (cons 41  0.00000000)
          (cons 42  -0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.71977892 -0.03659564 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.72943321 -0.03850215 0.00000000)
          (cons 40  0.00000000)
          (cons 41  0.00000000)
          (cons 42  0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.74460567 -0.05452957 0.00000000)
          (cons 40  0.00000000)
          (cons 41  0.00000000)
          (cons 42  0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.74711080 -0.13063449 0.00000000)
          (cons 40  0.00000000)
          (cons 41  0.00000000)
          (cons 42  0.30975875)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.73364997 -0.14744680 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.69057987 -0.16052900 0.00000000)
          (cons 40  0.00000000)
          (cons 41  0.00000000)
          (cons 42  -0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.68944687 -0.16213983 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.68985971 -0.17039648 0.00000000)
          (cons 40  0.00000000)
          (cons 41  0.00000000)
          (cons 42  -0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.69153761 -0.17191458 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.75970246 -0.16850634 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82786731 -0.16509810 0.00000000)
          (cons 40  0.00000000)
          (cons 41  0.00000000)
          (cons 42  -0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82938541 -0.16342019 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82897258 -0.15516355 0.00000000)
          (cons 40  0.00000000)
          (cons 41  0.00000000)
          (cons 42  -0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82768455 -0.15367376 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78352430 -0.14495308 0.00000000)
          (cons 40  0.00000000)
          (cons 41  0.00000000)
          (cons 42  0.30975875)
          (cons 91 0)
          (cons 70 0)
          (cons 50  0.00000000)
         )
         (list
          (cons 0 "SEQEND")
          (cons 100 "AcDbEntity")
          (cons 67 0)
          (cons 8 "0")
          (cons 62 1)
         )
         (list
          (cons 0 "ARC")
          (cons 100 "AcDbEntity")
          (cons 67 0)
          (cons 8 "0")
          (cons 62 1)
          (cons 6 "Continuous")
          (cons 100 "AcDbCircle")
          (list 10 -0.88224768 -0.16174327 0.00000000)
          (cons 40  0.00635001)
          (list 210 0.00000000 0.00000000 1.00000000)
          (cons 100 "AcDbArc")
          (cons 50  4.66243086)
          (cons 51  5.75958867)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.92306764 -0.33173376 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.92306764 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.86303724 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.86303724 -0.33173376 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "LINE")
          (cons 100 "AcDbEntity")
          (cons 67 0)
          (cons 8 "0")
          (cons 62 1)
          (cons 6 "Continuous")
          (cons 100 "AcDbLine")
          (list 10 -0.84091894 -0.21038376 0.00000000)
          (list 11 -0.95109144 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.85330144 -0.20809776 0.00000000)
          (list 11 -0.95217094 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.95217094 -0.21673376 0.00000000)
          (list 11 -0.75970244 -0.21673376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85787146 -0.15838433 0.00000000)
          (cons 40  0.02540000)
          (list 210 0.00000000 0.00000000 1.00000000)
          (cons 100 "AcDbArc")
          (cons 50  0.18065653)
          (cons 51  2.87664897)
         )
         (list
          (cons 0 "LINE")
          (cons 100 "AcDbEntity")
          (cons 67 0)
          (cons 8 "0")
          (cons 62 1)
          (cons 6 "Continuous")
          (cons 100 "AcDbLine")
          (list 10 -0.91306764 -0.20085876 0.00000000)
          (list 11 -0.87303724 -0.20085876 0.00000000)
          (list 210 0.00000000 0.00000000 1.00000000)
         )
         (list
          (cons 0 "LINE")
          (cons 100 "AcDbEntity")
          (cons 67 0)
          (cons 8 "0")
          (cons 62 1)
          (cons 100 "AcDbLine")
          (list 10 -0.87825461 -0.13505188 0.00000000)
          (list 11 -0.87255840 -0.13766107 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.86919991 -0.15184384 0.00000000)
          (list 11 -0.87674841 -0.16491827 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.87861689 -0.19491855 0.00000000)
          (cons 40  0.00759460)
          (list 210 0.00000000 0.00000000 1.00000000)
          (cons 100 "AcDbArc")
          (cons 50  0.88461343)
          (cons 51  2.25697923)
         )
         (list
          (cons 0 "LINE")
          (cons 100 "AcDbEntity")
          (cons 67 0)
          (cons 8 "0")
          (cons 62 1)
          (cons 6 "Continuous")
          (cons 100 "AcDbLine")
          (list 10 -0.91306764 -0.20809776 0.00000000)
          (list 11 -0.87303724 -0.20809776 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85755097 -0.15373334 0.00000000)
          (cons 40  0.02788666)
          (list 210 0.00000000 0.00000000 1.00000000)
          (cons 100 "AcDbArc")
          (cons 50  1.24743899)
          (cons 51  2.47348806)
         )
         (list
          (cons 0 "ARC")
          (cons 100 "AcDbEntity")
          (cons 67 0)
          (cons 8 "0")
          (cons 62 1)
          (cons 100 "AcDbCircle")
          (list 10 -0.85755101 -0.15373332 0.00000000)
          (cons 40  0.04795266)
          (list 210 0.00000000 0.00000000 1.00000000)
          (cons 100 "AcDbArc")
          (cons 50  1.45175629)
          (cons 51  2.87134456)
         )
         (list
          (cons 0 "ARC")
          (cons 100 "AcDbEntity")
          (cons 67 0)
          (cons 8 "0")
          (cons 62 1)
          (cons 6 "Continuous")
          (cons 100 "AcDbCircle")
          (list 10 -0.90857715 -0.16441111 0.00000000)
          (cons 40  0.00317500)
          (list 210 0.00000000 0.00000000 1.00000000)
          (cons 100 "AcDbArc")
          (cons 50  5.14873404)
          (cons 51  6.24828281)
         )
         (list
          (cons 0 "LINE")
          (cons 100 "AcDbEntity")
          (cons 67 0)
          (cons 8 "0")
          (cons 62 1)
          (cons 6 "Continuous")
          (cons 100 "AcDbLine")
          (list 10 -0.90505918 -0.15464920 0.00000000)
          (list 11 -0.90616280 -0.18625376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89620743 -0.17045610 0.00000000)
          (cons 40  0.00304800)
          (list 210 0.00000000 0.00000000 1.00000000)
          (cons 100 "AcDbArc")
          (cons 50  1.52084581)
          (cons 51  3.10633488)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 -0.96988744 -0.21992629 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.91055244 -0.21992629 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "LINE")
          (cons 100 "AcDbEntity")
          (cons 67 0)
          (cons 8 "0")
          (cons 62 1)
          (cons 6 "Continuous")
          (cons 100 "AcDbLine")
          (list 10 -0.94055951 -0.18282803 0.00000000)
          (list 11 -0.90723517 -0.16728862 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.94461444 -0.18625376 0.00000000)
          (list 11 -0.90416494 -0.18625376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.95096444 -0.20174776 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.95109144 -0.21673376 0.00000000)
          (list 11 -0.95109144 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.95193892 -0.21673376 0.00000000)
          (list 11 -0.95109144 -0.21588629 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.95217094 -0.21673376 0.00000000)
          (list 11 -0.95217094 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.94143944 -0.18420924 0.00000000)
          (list 11 -0.94143944 -0.18625376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.94461444 -0.20174776 0.00000000)
          (list 11 -0.94461444 -0.18625376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.93991545 -0.18420925 0.00000000)
          (cons 40  0.00152400)
          (list 210 0.00000000 0.00000000 1.00000000)
          (cons 100 "AcDbArc")
          (cons 50  2.00712794)
          (cons 51  3.14158597)
         )
         (list
          (cons 0 "LINE")
          (cons 100 "AcDbEntity")
          (cons 67 0)
          (cons 8 "0")
          (cons 62 1)
          (cons 6 "Continuous")
          (cons 100 "AcDbLine")
          (list 10 -0.90416494 -0.21673376 0.00000000)
          (list 11 -0.90416494 -0.33173376 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.90340294 -0.33173376 0.00000000)
          (list 11 -0.90340294 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88193994 -0.21673376 0.00000000)
          (list 11 -0.88193994 -0.33173376 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.88270194 -0.33173376 0.00000000)
          (list 11 -0.88270194 -0.21673376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.90748800 -0.19491855 0.00000000)
          (cons 40  0.00759460)
          (list 210 0.00000000 0.00000000 1.00000000)
          (cons 100 "AcDbArc")
          (cons 50  0.88461343)
          (cons 51  2.25697923)
         )
         (list
          (cons 0 "LINE")
          (cons 100 "AcDbEntity")
          (cons 67 0)
          (cons 8 "0")
          (cons 62 1)
          (cons 6 "Continuous")
          (cons 100 "AcDbLine")
          (list 10 -0.91229985 -0.20085876 0.00000000)
          (list 11 -0.91229985 -0.18904283 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.92096974 -0.21038376 0.00000000)
          (list 11 -0.92096974 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.92797744 -0.21038376 0.00000000)
          (list 11 -0.92797744 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.91306764 -0.20085876 0.00000000)
          (list 11 -0.91306764 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.93280344 -0.20809776 0.00000000)
          (list 11 -0.93280344 -0.21038376 0.00000000)
          (list 210 0.00000000 0.00000000 1.00000000)
         )
         (list
          (cons 0 "LINE")
          (cons 100 "AcDbEntity")
          (cons 67 0)
          (cons 8 "0")
          (cons 62 1)
          (cons 100 "AcDbLine")
          (list 10 -0.90416494 -0.17042964 0.00000000)
          (list 11 -0.88193994 -0.17042964 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89305244 -0.21512155 0.00000000)
          (cons 40  0.02779776)
          (list 210 0.00000000 0.00000000 1.00000000)
          (cons 100 "AcDbArc")
          (cons 50  1.21727415)
          (cons 51  1.92431851)
         )
         (list
          (cons 0 "LINE")
          (cons 100 "AcDbEntity")
          (cons 67 0)
          (cons 8 "0")
          (cons 62 1)
          (cons 6 "Continuous")
          (cons 100 "AcDbLine")
          (list 10 -0.87861689 -0.18732373 0.00000000)
          (list 11 -0.90748800 -0.18732373 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90267615 -0.18904283 0.00000000)
          (list 11 -0.90267615 -0.20085876 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.90340294 -0.18732373 0.00000000)
          (list 11 -0.90340294 -0.17042964 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90416494 -0.17042964 0.00000000)
          (list 11 -0.90416494 -0.18732373 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89925352 -0.17034866 0.00000000)
          (list 11 -0.89925635 -0.17042964 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89605518 -0.16741082 0.00000000)
          (list 11 -0.88256478 -0.16808534 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88342874 -0.18904283 0.00000000)
          (list 11 -0.88342874 -0.20085876 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.88270194 -0.18732373 0.00000000)
          (list 11 -0.88270194 -0.17042964 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88193994 -0.17042964 0.00000000)
          (list 11 -0.88193994 -0.18732373 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89559430 -0.20809776 0.00000000)
          (list 11 -0.88835530 -0.20085876 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89774959 -0.20809776 0.00000000)
          (list 11 -0.89051059 -0.20085876 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.90351318 -0.15470353 0.00000000)
          (list 11 -0.88597339 -0.15558051 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90345999 -0.15318029 0.00000000)
          (list 11 -0.88560793 -0.15407287 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89447511 -0.14511019 0.00000000)
          (cons 40  0.01003300)
          (list 210 0.00000000 0.00000000 1.00000000)
          (cons 100 "AcDbArc")
          (cons 50  2.92404561)
          (cons 51  4.10397118)
         )
         (list
          (cons 0 "LINE")
          (cons 100 "AcDbEntity")
          (cons 67 0)
          (cons 8 "0")
          (cons 62 1)
          (cons 6 "Continuous")
          (cons 100 "AcDbLine")
          (list 10 -0.90376304 -0.14093246 0.00000000)
          (list 11 -0.90426533 -0.14294793 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.90353610 -0.15470244 0.00000000)
          (cons 40  0.00152400)
          (list 210 0.00000000 0.00000000 1.00000000)
          (cons 100 "AcDbArc")
          (cons 50  1.52083960)
          (cons 51  3.10668034)
         )
         (list
          (cons 0 "ARC")
          (cons 100 "AcDbEntity")
          (cons 67 0)
          (cons 8 "0")
          (cons 62 1)
          (cons 6 "Continuous")
          (cons 100 "AcDbCircle")
          (list 10 -0.90358963 -0.15622561 0.00000000)
          (cons 40  0.00152400)
          (list 210 0.00000000 0.00000000 1.00000000)
          (cons 100 "AcDbArc")
          (cons 50  1.52081044)
          (cons 51  3.10669071)
         )
         (list
          (cons 0 "ARC")
          (cons 100 "AcDbEntity")
          (cons 67 0)
          (cons 8 "0")
          (cons 62 1)
          (cons 100 "AcDbCircle")
          (list 10 -0.89447511 -0.14511019 0.00000000)
          (cons 40  0.01003300)
          (list 210 0.00000000 0.00000000 1.00000000)
          (cons 100 "AcDbArc")
          (cons 50  5.22089241)
          (cons 51  6.03683623)
         )
         (list
          (cons 0 "LINE")
          (cons 100 "AcDbEntity")
          (cons 67 0)
          (cons 8 "0")
          (cons 62 1)
          (cons 100 "AcDbLine")
          (list 10 -0.88791250 -0.15269894 0.00000000)
          (list 11 -0.88498040 -0.15404201 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.88581494 -0.15240948 0.00000000)
          (cons 40  0.00317500)
          (list 210 0.00000000 0.00000000 1.00000000)
          (cons 100 "AcDbArc")
          (cons 50  4.66241596)
          (cons 51  6.07254591)
         )
         (list
          (cons 0 "ARC")
          (cons 100 "AcDbEntity")
          (cons 67 0)
          (cons 8 "0")
          (cons 62 1)
          (cons 6 "Continuous")
          (cons 100 "AcDbCircle")
          (list 10 -0.88544940 -0.15090185 0.00000000)
          (cons 40  0.00317500)
          (list 210 0.00000000 0.00000000 1.00000000)
          (cons 100 "AcDbArc")
          (cons 50  4.66243394)
          (cons 51  6.01824134)
         )
         (list
          (cons 0 "ARC")
          (cons 100 "AcDbEntity")
          (cons 67 0)
          (cons 8 "0")
          (cons 62 1)
          (cons 100 "AcDbCircle")
          (list 10 -0.85755089 -0.15373311 0.00000000)
          (cons 40  0.02788666)
          (list 210 0.00000000 0.00000000 1.00000000)
          (cons 100 "AcDbArc")
          (cons 50  2.47348747)
          (cons 51  2.91826494)
         )
         (list
          (cons 0 "LINE")
          (cons 100 "AcDbEntity")
          (cons 67 0)
          (cons 8 "0")
          (cons 62 1)
          (cons 6 "Continuous")
          (cons 100 "AcDbLine")
          (list 10 -0.84654296 -0.16492484 0.00000000)
          (list 11 -0.85777616 -0.18438135 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84707844 -0.20174776 0.00000000)
          (list 11 -0.84707844 -0.16585233 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84335823 -0.15881190 0.00000000)
          (list 11 -0.84452867 -0.19232916 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.81461567 -0.21092434 0.00000000)
          (cons 40  0.00152400)
          (list 210 0.00000000 0.00000000 1.00000000)
          (cons 100 "AcDbArc")
          (cons 50  4.71238705)
          (cons 51  6.23082632)
         )
         (list
          (cons 0 "LINE")
          (cons 100 "AcDbEntity")
          (cons 67 0)
          (cons 8 "0")
          (cons 62 1)
          (cons 6 "Continuous")
          (cons 100 "AcDbLine")
          (list 10 -0.82509322 -0.21482876 0.00000000)
          (list 11 -0.75970244 -0.21482876 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.86327543 -0.18120634 0.00000000)
          (cons 40  0.00635001)
          (list 210 0.00000000 0.00000000 1.00000000)
          (cons 100 "AcDbArc")
          (cons 50  4.71238703)
          (cons 51  5.75958588)
         )
         (list
          (cons 0 "LINE")
          (cons 100 "AcDbEntity")
          (cons 67 0)
          (cons 8 "0")
          (cons 62 1)
          (cons 6 "Continuous")
          (cons 100 "AcDbLine")
          (list 10 -0.87380504 -0.18904283 0.00000000)
          (list 11 -0.87380504 -0.20085876 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.87380504 -0.18755635 0.00000000)
          (list 11 -0.86327544 -0.18755635 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.85812744 -0.21038376 0.00000000)
          (list 11 -0.85812744 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.86513515 -0.21038376 0.00000000)
          (list 11 -0.86513515 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.87303724 -0.20085876 0.00000000)
          (list 11 -0.87303724 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.85330144 -0.20809649 0.00000000)
          (list 11 -0.85330144 -0.21038376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85342844 -0.20174776 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.84300559 -0.19390635 0.00000000)
          (list 11 -0.83113834 -0.19390635 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.84300559 -0.19238235 0.00000000)
          (cons 40  0.00152400)
          (list 210 0.00000000 0.00000000 1.00000000)
          (cons 100 "AcDbArc")
          (cons 50  3.10668656)
          (cons 51  4.71238898)
         )
         (list
          (cons 0 "ARC")
          (cons 100 "AcDbEntity")
          (cons 67 0)
          (cons 8 "0")
          (cons 62 1)
          (cons 6 "Continuous")
          (cons 100 "AcDbCircle")
          (list 10 -0.83113834 -0.20178054 0.00000000)
          (cons 40  0.00787400)
          (list 210 0.00000000 0.00000000 1.00000000)
          (cons 100 "AcDbArc")
          (cons 50  0.05236240)
          (cons 51  1.57079607)
         )
         (list
          (cons 0 "LINE")
          (cons 100 "AcDbEntity")
          (cons 67 0)
          (cons 8 "0")
          (cons 62 1)
          (cons 6 "Continuous")
          (cons 100 "AcDbLine")
          (list 10 -0.83456894 -0.20149376 0.00000000)
          (list 11 -0.83088594 -0.20149376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.83456894 -0.20149376 0.00000000)
          (list 11 -0.83456894 -0.20403376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.82504652 -0.20322575 0.00000000)
          (cons 40  0.00111252)
          (list 210 0.00000000 0.00000000 1.00000000)
          (cons 100 "AcDbArc")
          (cons 50  0.05236168)
          (cons 51  3.10668488)
         )
         (list
          (cons 0 "ARC")
          (cons 100 "AcDbEntity")
          (cons 67 0)
          (cons 8 "0")
          (cons 62 1)
          (cons 6 "Continuous")
          (cons 100 "AcDbCircle")
          (list 10 -0.82124822 -0.21092434 0.00000000)
          (cons 40  0.00152400)
          (list 210 0.00000000 0.00000000 1.00000000)
          (cons 100 "AcDbArc")
          (cons 50  3.19394763)
          (cons 51  4.71238690)
         )
         (list
          (cons 0 "ARC")
          (cons 100 "AcDbEntity")
          (cons 67 0)
          (cons 8 "0")
          (cons 62 1)
          (cons 6 "Continuous")
          (cons 100 "AcDbCircle")
          (list 10 -0.82115506 -0.21254209 0.00000000)
          (cons 40  0.00228600)
          (list 210 0.00000000 0.00000000 1.00000000)
          (cons 100 "AcDbArc")
          (cons 50  3.19393752)
          (cons 51  4.71238789)
         )
         (list
          (cons 0 "ARC")
          (cons 100 "AcDbEntity")
          (cons 67 0)
          (cons 8 "0")
          (cons 62 1)
          (cons 100 "AcDbCircle")
          (list 10 -0.83456894 -0.21038376 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.82821894 -0.20416076 0.00000000)
          (list 11 -0.82821894 -0.21038376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.82509321 -0.21635275 0.00000000)
          (cons 40  0.00152399)
          (list 210 0.00000000 0.00000000 1.00000000)
          (cons 100 "AcDbArc")
          (cons 50  1.57080019)
          (cons 51  3.10668917)
         )
         (list
          (cons 0 "LINE")
          (cons 100 "AcDbEntity")
          (cons 67 0)
          (cons 8 "0")
          (cons 62 1)
          (cons 6 "Continuous")
          (cons 100 "AcDbLine")
          (list 10 -0.82124822 -0.21244835 0.00000000)
          (list 11 -0.81461567 -0.21244835 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.83088594 -0.20416076 0.00000000)
          (cons 40  0.00266700)
          (list 210 0.00000000 0.00000000 1.00000000)
          (cons 100 "AcDbArc")
          (cons 50  0.00000000)
          (cons 51  1.57079633)
         )
         (list
          (cons 0 "ARC")
          (cons 100 "AcDbEntity")
          (cons 67 0)
          (cons 8 "0")
          (cons 62 1)
          (cons 6 "Continuous")
          (cons 100 "AcDbCircle")
          (list 10 -0.84091894 -0.20403376 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.82615836 -0.20318692 0.00000000)
          (list 11 -0.82663144 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.82343790 -0.21266239 0.00000000)
          (list 11 -0.82393553 -0.20316752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.82277014 -0.21100410 0.00000000)
          (list 11 -0.82327511 -0.20136826 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.80667000 -0.19035035 0.00000000)
          (cons 40  0.00228600)
          (list 210 0.00000000 0.00000000 1.00000000)
          (cons 100 "AcDbArc")
          (cons 50  1.57079633)
          (cons 51  3.08923306)
         )
         (list
          (cons 0 "ARC")
          (cons 100 "AcDbEntity")
          (cons 67 0)
          (cons 8 "0")
          (cons 62 1)
          (cons 6 "Continuous")
          (cons 100 "AcDbCircle")
          (list 10 -0.80871884 -0.18819135 0.00000000)
          (cons 40  0.00317500)
          (list 210 0.00000000 0.00000000 1.00000000)
          (cons 100 "AcDbArc")
          (cons 50  1.57079503)
          (cons 51  3.08923156)
         )
         (list
          (cons 0 "ARC")
          (cons 100 "AcDbEntity")
          (cons 67 0)
          (cons 8 "0")
          (cons 62 1)
          (cons 6 "Continuous")
          (cons 100 "AcDbCircle")
          (list 10 -0.81241133 -0.21254275 0.00000000)
          (cons 40  0.00228600)
          (list 210 0.00000000 0.00000000 1.00000000)
          (cons 100 "AcDbArc")
          (cons 50  4.71238705)
          (cons 51  6.23082632)
         )
         (list
          (cons 0 "LINE")
          (cons 100 "AcDbEntity")
          (cons 67 0)
          (cons 8 "0")
          (cons 62 1)
          (cons 6 "Continuous")
          (cons 100 "AcDbLine")
          (list 10 -0.81309375 -0.21100410 0.00000000)
          (list 11 -0.81188949 -0.18802518 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.81012846 -0.21266239 0.00000000)
          (list 11 -0.80895287 -0.19023071 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85862670 -0.16286834 0.00000000)
          (cons 40  0.05715000)
          (list 210 0.00000000 0.00000000 1.00000000)
          (cons 100 "AcDbArc")
          (cons 50  0.39733728)
          (cons 51  1.45204144)
         )
         (list
          (cons 0 "ARC")
          (cons 100 "AcDbEntity")
          (cons 67 0)
          (cons 8 "0")
          (cons 62 1)
          (cons 6 "Continuous")
          (cons 100 "AcDbCircle")
          (list 10 -0.85787146 -0.15838434 0.00000000)
          (cons 40  0.01308100)
          (list 210 0.00000000 0.00000000 1.00000000)
          (cons 100 "AcDbArc")
          (cons 50  5.75958633)
          (cons 51  2.61799368)
         )
         (list
          (cons 0 "ARC")
          (cons 100 "AcDbEntity")
          (cons 67 0)
          (cons 8 "0")
          (cons 62 1)
          (cons 100 "AcDbCircle")
          (list 10 -0.86047397 -0.16245432 0.00000000)
          (cons 40  0.03708400)
          (list 210 0.00000000 0.00000000 1.00000000)
          (cons 100 "AcDbArc")
          (cons 50  0.48069660)
          (cons 51  1.24742577)
         )
         (list
          (cons 0 "CIRCLE")
          (cons 100 "AcDbEntity")
          (cons 67 0)
          (cons 8 "0")
          (cons 62 1)
          (cons 100 "AcDbCircle")
          (list 10 -0.85805989 -0.15533774 0.00000000)
          (cons 40  0.01003300)
          (list 210 0.00000000 0.00000000 1.00000000)
         )
         (list
          (cons 0 "ARC")
          (cons 100 "AcDbEntity")
          (cons 67 0)
          (cons 8 "0")
          (cons 62 1)
          (cons 100 "AcDbCircle")
          (list 10 -0.85787144 -0.15314603 0.00000000)
          (cons 40  0.01008126)
          (list 210 0.00000000 0.00000000 1.00000000)
          (cons 100 "AcDbArc")
          (cons 50  0.40917332)
          (cons 51  2.73241869)
         )
         (list
          (cons 0 "LINE")
          (cons 100 "AcDbEntity")
          (cons 67 0)
          (cons 8 "0")
          (cons 62 1)
          (cons 100 "AcDbLine")
          (list 10 -0.87350405 -0.15929885 0.00000000)
          (list 11 -0.86223810 -0.16445931 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84483212 -0.15734109 0.00000000)
          (list 11 -0.83245244 -0.15734109 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84483212 -0.15734109 0.00000000)
          (list 11 -0.83245244 -0.15734109 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.84183517 -0.15886508 0.00000000)
          (cons 40  0.00152399)
          (list 210 0.00000000 0.00000000 1.00000000)
          (cons 100 "AcDbArc")
          (cons 50  1.57080019)
          (cons 51  3.10668917)
         )
         (list
          (cons 0 "LINE")
          (cons 100 "AcDbEntity")
          (cons 67 0)
          (cons 8 "0")
          (cons 62 1)
          (cons 6 "Continuous")
          (cons 100 "AcDbLine")
          (list 10 -0.83072344 -0.16273689 0.00000000)
          (list 11 -0.83611921 -0.15734109 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.82189069 -0.15181245 0.00000000)
          (cons 40  0.01117600)
          (list 210 0.00000000 0.00000000 1.00000000)
          (cons 100 "AcDbArc")
          (cons 50  3.32225661)
          (cons 51  3.73034794)
         )
         (list
          (cons 0 "ARC")
          (cons 100 "AcDbEntity")
          (cons 67 0)
          (cons 8 "0")
          (cons 62 1)
          (cons 100 "AcDbCircle")
          (list 10 -0.83245244 -0.15886509 0.00000000)
          (cons 40  0.00152400)
          (list 210 0.00000000 0.00000000 1.00000000)
          (cons 100 "AcDbArc")
          (cons 50  0.05235839)
          (cons 51  1.57080045)
         )
         (list
          (cons 0 "ARC")
          (cons 100 "AcDbEntity")
          (cons 67 0)
          (cons 8 "0")
          (cons 62 1)
          (cons 6 "Continuous")
          (cons 100 "AcDbCircle")
          (list 10 -0.82915694 -0.16350769 0.00000000)
          (cons 40  0.00152400)
          (list 210 0.00000000 0.00000000 1.00000000)
          (cons 100 "AcDbArc")
          (cons 50  3.19395084)
          (cons 51  4.66241844)
         )
         (list
          (cons 0 "LINE")
          (cons 100 "AcDbEntity")
          (cons 67 0)
          (cons 8 "0")
          (cons 62 1)
          (cons 6 "Continuous")
          (cons 100 "AcDbLine")
          (list 10 -0.83067886 -0.16358746 0.00000000)
          (list 11 -0.83093052 -0.15878533 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.82211799 -0.14583452 0.00000000)
          (cons 40  0.00709647)
          (list 210 0.00000000 0.00000000 1.00000000)
          (cons 100 "AcDbArc")
          (cons 50  2.77219369)
          (cons 51  4.52091742)
         )
         (list
          (cons 0 "ARC")
          (cons 100 "AcDbEntity")
          (cons 67 0)
          (cons 8 "0")
          (cons 62 1)
          (cons 100 "AcDbCircle")
          (list 10 -0.81066054 -0.14355768 0.00000000)
          (cons 40  0.00664210)
          (list 210 0.00000000 0.00000000 1.00000000)
          (cons 100 "AcDbArc")
          (cons 50  5.02355404)
          (cons 51  1.02870600)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.59633724 -0.33173376 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.59633724 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.65636764 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.65636764 -0.33173376 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "LINE")
          (cons 100 "AcDbEntity")
          (cons 67 0)
          (cons 8 "0")
          (cons 62 1)
          (cons 6 "Continuous")
          (cons 100 "AcDbLine")
          (list 10 -0.63328549 -0.16516317 0.00000000)
          (list 11 -0.61516380 -0.16606922 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.63298516 -0.16670406 0.00000000)
          (list 11 -0.61511043 -0.16759781 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62431267 -0.15378646 0.00000000)
          (cons 40  0.01003300)
          (list 210 0.00000000 0.00000000 1.00000000)
          (cons 100 "AcDbArc")
          (cons 50  6.21237415)
          (cons 51  3.14633739)
         )
         (list
          (cons 0 "LINE")
          (cons 100 "AcDbEntity")
          (cons 67 0)
          (cons 8 "0")
          (cons 62 1)
          (cons 6 "Continuous")
          (cons 100 "AcDbLine")
          (list 10 -0.63641222 -0.17886711 0.00000000)
          (list 11 -0.62244217 -0.17956561 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.66129223 -0.18755635 0.00000000)
          (list 11 -0.62252809 -0.18755635 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.66190186 -0.16351122 0.00000000)
          (cons 40  0.04795206)
          (list 210 0.00000000 0.00000000 1.00000000)
          (cons 100 "AcDbArc")
          (cons 50  0.34986041)
          (cons 51  1.55890984)
         )
         (list
          (cons 0 "LINE")
          (cons 100 "AcDbEntity")
          (cons 67 0)
          (cons 8 "0")
          (cons 62 1)
          (cons 6 "Continuous")
          (cons 100 "AcDbLine")
          (list 10 -0.56831344 -0.21038376 0.00000000)
          (list 11 -0.62584444 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.62876544 -0.19390635 0.00000000)
          (list 11 -0.57945136 -0.19267351 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.63282661 -0.16353302 0.00000000)
          (cons 40  0.00317500)
          (list 210 0.00000000 0.00000000 1.00000000)
          (cons 100 "AcDbArc")
          (cons 50  3.30661926)
          (cons 51  4.66242980)
         )
         (list
          (cons 0 "LINE")
          (cons 100 "AcDbEntity")
          (cons 67 0)
          (cons 8 "0")
          (cons 62 1)
          (cons 6 "Continuous")
          (cons 100 "AcDbLine")
          (list 10 -0.64968491 -0.16168680 0.00000000)
          (list 11 -0.64159438 -0.17570003 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.68871844 -0.17053332 0.00000000)
          (list 11 -0.68847437 -0.16587582 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.66101340 -0.16822728 0.00000000)
          (cons 40  0.01308100)
          (list 210 0.00000000 0.00000000 1.00000000)
          (cons 100 "AcDbArc")
          (cons 50  0.52359898)
          (cons 51  3.66519163)
         )
         (list
          (cons 0 "CIRCLE")
          (cons 100 "AcDbEntity")
          (cons 67 0)
          (cons 8 "0")
          (cons 62 1)
          (cons 100 "AcDbCircle")
          (list 10 -0.66115168 -0.16517839 0.00000000)
          (cons 40  0.01003300)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.68483594 -0.21038376 0.00000000)
          (cons 40  0.00635000)
          (list 210 0.00000000 0.00000000 1.00000000)
          (cons 100 "AcDbArc")
          (cons 50  3.14159265)
          (cons 51  4.71238898)
         )
         (list
          (cons 0 "LINE")
          (cons 100 "AcDbEntity")
          (cons 67 0)
          (cons 8 "0")
          (cons 62 1)
          (cons 6 "Continuous")
          (cons 100 "AcDbLine")
          (list 10 -0.68851894 -0.20149376 0.00000000)
          (list 11 -0.68483594 -0.20149376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.68826657 -0.19390635 0.00000000)
          (list 11 -0.62876544 -0.19390635 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.68851894 -0.20416076 0.00000000)
          (cons 40  0.00266700)
          (list 210 0.00000000 0.00000000 1.00000000)
          (cons 100 "AcDbArc")
          (cons 50  1.57079633)
          (cons 51  3.14159265)
         )
         (list
          (cons 0 "LINE")
          (cons 100 "AcDbEntity")
          (cons 67 0)
          (cons 8 "0")
          (cons 62 1)
          (cons 6 "Continuous")
          (cons 100 "AcDbLine")
          (list 10 -0.69118594 -0.20416076 0.00000000)
          (list 11 -0.69118594 -0.21038376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.69024034 -0.17045348 0.00000000)
          (cons 40  0.00152400)
          (list 210 0.00000000 0.00000000 1.00000000)
          (cons 100 "AcDbArc")
          (cons 50  4.66243298)
          (cons 51  6.23083137)
         )
         (list
          (cons 0 "ARC")
          (cons 100 "AcDbEntity")
          (cons 67 0)
          (cons 8 "0")
          (cons 62 1)
          (cons 100 "AcDbCircle")
          (list 10 -0.69431261 -0.21635276 0.00000000)
          (cons 40  0.00152400)
          (list 210 0.00000000 0.00000000 1.00000000)
          (cons 100 "AcDbArc")
          (cons 50  0.00000000)
          (cons 51  1.57079633)
         )
         (list
          (cons 0 "ARC")
          (cons 100 "AcDbEntity")
          (cons 67 0)
          (cons 8 "0")
          (cons 62 1)
          (cons 6 "Continuous")
          (cons 100 "AcDbCircle")
          (list 10 -0.69435837 -0.20322575 0.00000000)
          (cons 40  0.00111252)
          (list 210 0.00000000 0.00000000 1.00000000)
          (cons 100 "AcDbArc")
          (cons 50  0.03490778)
          (cons 51  3.08923097)
         )
         (list
          (cons 0 "ARC")
          (cons 100 "AcDbEntity")
          (cons 67 0)
          (cons 8 "0")
          (cons 62 1)
          (cons 6 "Continuous")
          (cons 100 "AcDbCircle")
          (list 10 -0.69824985 -0.21254276 0.00000000)
          (cons 40  0.00228600)
          (list 210 0.00000000 0.00000000 1.00000000)
          (cons 100 "AcDbArc")
          (cons 50  4.71238898)
          (cons 51  6.23082363)
         )
         (list
          (cons 0 "LINE")
          (cons 100 "AcDbEntity")
          (cons 67 0)
          (cons 8 "0")
          (cons 62 1)
          (cons 100 "AcDbLine")
          (list 10 -0.69278861 -0.21635276 0.00000000)
          (list 11 -0.69278861 -0.21673376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.69815666 -0.21092435 0.00000000)
          (cons 40  0.00152400)
          (list 210 0.00000000 0.00000000 1.00000000)
          (cons 100 "AcDbArc")
          (cons 50  4.71238898)
          (cons 51  6.23082707)
         )
         (list
          (cons 0 "LINE")
          (cons 100 "AcDbEntity")
          (cons 67 0)
          (cons 8 "0")
          (cons 62 1)
          (cons 6 "Continuous")
          (cons 100 "AcDbLine")
          (list 10 -0.70478923 -0.21244835 0.00000000)
          (list 11 -0.69815666 -0.21244835 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69324653 -0.20318692 0.00000000)
          (list 11 -0.69277344 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69663475 -0.21100410 0.00000000)
          (list 11 -0.69612978 -0.20136827 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69596699 -0.21266240 0.00000000)
          (list 11 -0.69546936 -0.20316752 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.71068606 -0.18819133 0.00000000)
          (cons 40  0.00317500)
          (list 210 0.00000000 0.00000000 1.00000000)
          (cons 100 "AcDbArc")
          (cons 50  0.05235860)
          (cons 51  1.57079513)
         )
         (list
          (cons 0 "ARC")
          (cons 100 "AcDbEntity")
          (cons 67 0)
          (cons 8 "0")
          (cons 62 1)
          (cons 6 "Continuous")
          (cons 100 "AcDbCircle")
          (list 10 -0.71273486 -0.19035035 0.00000000)
          (cons 40  0.00228600)
          (list 210 0.00000000 0.00000000 1.00000000)
          (cons 100 "AcDbArc")
          (cons 50  0.05235847)
          (cons 51  1.57079633)
         )
         (list
          (cons 0 "ARC")
          (cons 100 "AcDbEntity")
          (cons 67 0)
          (cons 8 "0")
          (cons 62 1)
          (cons 100 "AcDbCircle")
          (list 10 -0.70699357 -0.21254276 0.00000000)
          (cons 40  0.00228600)
          (list 210 0.00000000 0.00000000 1.00000000)
          (cons 100 "AcDbArc")
          (cons 50  3.19395112)
          (cons 51  4.71238898)
         )
         (list
          (cons 0 "LINE")
          (cons 100 "AcDbEntity")
          (cons 67 0)
          (cons 8 "0")
          (cons 62 1)
          (cons 6 "Continuous")
          (cons 100 "AcDbLine")
          (list 10 -0.70927643 -0.21266239 0.00000000)
          (list 11 -0.71045200 -0.19023071 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.70631114 -0.21100411 0.00000000)
          (list 11 -0.70751540 -0.18802518 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.70478923 -0.21092435 0.00000000)
          (cons 40  0.00152400)
          (list 210 0.00000000 0.00000000 1.00000000)
          (cons 100 "AcDbArc")
          (cons 50  3.19395212)
          (cons 51  4.71238898)
         )
         (list
          (cons 0 "ARC")
          (cons 100 "AcDbEntity")
          (cons 67 0)
          (cons 8 "0")
          (cons 62 1)
          (cons 6 "Continuous")
          (cons 100 "AcDbCircle")
          (list 10 -0.68826657 -0.20178035 0.00000000)
          (cons 40  0.00787400)
          (list 210 0.00000000 0.00000000 1.00000000)
          (cons 100 "AcDbArc")
          (cons 50  1.57079633)
          (cons 51  3.08923442)
         )
         (list
          (cons 0 "LINE")
          (cons 100 "AcDbEntity")
          (cons 67 0)
          (cons 8 "0")
          (cons 62 1)
          (cons 6 "DASHED")
          (cons 100 "AcDbLine")
          (list 10 -0.63670294 -0.33173376 0.00000000)
          (list 11 -0.63670294 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.63746494 -0.21673376 0.00000000)
          (list 11 -0.63746494 -0.33173376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.64159244 -0.21038376 0.00000000)
          (list 11 -0.67848594 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.67234186 -0.17476780 0.00000000)
          (list 11 -0.66679148 -0.18438135 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.68483594 -0.20149376 0.00000000)
          (list 11 -0.68483594 -0.20403376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.67848594 -0.20403376 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 6 "Continuous")
          (cons 100 "AcDbCircle")
          (list 10 -0.66129222 -0.18120631 0.00000000)
          (cons 40  0.00635000)
          (list 210 0.00000000 0.00000000 1.00000000)
          (cons 100 "AcDbArc")
          (cons 50  3.66519355)
          (cons 51  4.71239040)
         )
         (list
          (cons 0 "ARC")
          (cons 100 "AcDbEntity")
          (cons 67 0)
          (cons 8 "0")
          (cons 62 1)
          (cons 6 "Continuous")
          (cons 100 "AcDbCircle")
          (list 10 -0.63609517 -0.17252491 0.00000000)
          (cons 40  0.00635000)
          (list 210 0.00000000 0.00000000 1.00000000)
          (cons 100 "AcDbArc")
          (cons 50  3.66519004)
          (cons 51  4.66242866)
         )
         (list
          (cons 0 "LINE")
          (cons 100 "AcDbEntity")
          (cons 67 0)
          (cons 8 "0")
          (cons 62 1)
          (cons 6 "Continuous")
          (cons 100 "AcDbLine")
          (list 10 -0.62584444 -0.21038376 0.00000000)
          (list 11 -0.62584444 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.64159244 -0.21038376 0.00000000)
          (list 11 -0.64159244 -0.21673376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.66014290 -0.17253922 0.00000000)
          (cons 40  0.03708400)
          (list 210 0.00000000 0.00000000 1.00000000)
          (cons 100 "AcDbArc")
          (cons 50  1.76322371)
          (cons 51  2.52595268)
         )
         (list
          (cons 0 "ARC")
          (cons 100 "AcDbEntity")
          (cons 67 0)
          (cons 8 "0")
          (cons 62 1)
          (cons 6 "Continuous")
          (cons 100 "AcDbCircle")
          (list 10 -0.68695245 -0.16595558 0.00000000)
          (cons 40  0.00152400)
          (list 210 0.00000000 0.00000000 1.00000000)
          (cons 100 "AcDbArc")
          (cons 50  2.33720068)
          (cons 51  3.08921738)
         )
         (list
          (cons 0 "ARC")
          (cons 100 "AcDbEntity")
          (cons 67 0)
          (cons 8 "0")
          (cons 62 1)
          (cons 100 "AcDbCircle")
          (list 10 -0.66202828 -0.17270793 0.00000000)
          (cons 40  0.05715000)
          (list 210 0.00000000 0.00000000 1.00000000)
          (cons 100 "AcDbArc")
          (cons 50  1.55860971)
          (cons 51  2.56947374)
         )
         (list
          (cons 0 "ARC")
          (cons 100 "AcDbEntity")
          (cons 67 0)
          (cons 8 "0")
          (cons 62 1)
          (cons 6 "Continuous")
          (cons 100 "AcDbCircle")
          (list 10 -0.70872048 -0.14826766 0.00000000)
          (cons 40  0.00664164)
          (list 210 0.00000000 0.00000000 1.00000000)
          (cons 100 "AcDbArc")
          (cons 50  1.39459995)
          (cons 51  4.16546659)
         )
         (list
          (cons 0 "LINE")
          (cons 100 "AcDbEntity")
          (cons 67 0)
          (cons 8 "0")
          (cons 62 1)
          (cons 6 "Continuous")
          (cons 100 "AcDbLine")
          (list 10 -0.69385434 -0.15761457 0.00000000)
          (list 11 -0.71444930 -0.15162817 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69316511 -0.14591171 0.00000000)
          (list 11 -0.70755637 -0.14172885 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.69750294 -0.15152840 0.00000000)
          (cons 40  0.00709676)
          (list 210 0.00000000 0.00000000 1.00000000)
          (cons 100 "AcDbArc")
          (cons 50  4.80779445)
          (cons 51  0.91316894)
         )
         (list
          (cons 0 "ARC")
          (cons 100 "AcDbEntity")
          (cons 67 0)
          (cons 8 "0")
          (cons 62 1)
          (cons 100 "AcDbCircle")
          (list 10 -0.66101339 -0.16822729 0.00000000)
          (cons 40  0.02540001)
          (list 210 0.00000000 0.00000000 1.00000000)
          (cons 100 "AcDbArc")
          (cons 50  0.16502661)
          (cons 51  2.82403160)
         )
         (list
          (cons 0 "ARC")
          (cons 100 "AcDbEntity")
          (cons 67 0)
          (cons 8 "0")
          (cons 62 1)
          (cons 6 "Continuous")
          (cons 100 "AcDbCircle")
          (list 10 -0.66190181 -0.16351112 0.00000000)
          (cons 40  0.02788609)
          (list 210 0.00000000 0.00000000 1.00000000)
          (cons 100 "AcDbArc")
          (cons 50  0.19774392)
          (cons 51  1.76322577)
         )
         (list
          (cons 0 "ARC")
          (cons 100 "AcDbEntity")
          (cons 67 0)
          (cons 8 "0")
          (cons 62 1)
          (cons 6 "Continuous")
          (cons 100 "AcDbCircle")
          (list 10 -0.69576061 -0.15680646 0.00000000)
          (cons 40  0.01117600)
          (list 210 0.00000000 0.00000000 1.00000000)
          (cons 100 "AcDbArc")
          (cons 50  5.47880514)
          (cons 51  5.96562864)
         )
         (list
          (cons 0 "LINE")
          (cons 100 "AcDbEntity")
          (cons 67 0)
          (cons 8 "0")
          (cons 62 1)
          (cons 6 "Continuous")
          (cons 100 "AcDbLine")
          (list 10 -0.63434133 -0.15349154 0.00000000)
          (list 11 -0.63440982 -0.15904690 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62457147 -0.15708018 0.00000000)
          (cons 40  0.01003300)
          (list 210 0.00000000 0.00000000 1.00000000)
          (cons 100 "AcDbArc")
          (cons 50  3.23667276)
          (cons 51  4.10386339)
         )
         (list
          (cons 0 "ARC")
          (cons 100 "AcDbEntity")
          (cons 67 0)
          (cons 8 "0")
          (cons 62 1)
          (cons 100 "AcDbCircle")
          (list 10 -0.63312695 -0.16199213 0.00000000)
          (cons 40  0.00317500)
          (list 210 0.00000000 0.00000000 1.00000000)
          (cons 100 "AcDbArc")
          (cons 50  3.36156540)
          (cons 51  4.66243282)
         )
         (list
          (cons 0 "ARC")
          (cons 100 "AcDbEntity")
          (cons 67 0)
          (cons 8 "0")
          (cons 62 1)
          (cons 6 "Continuous")
          (cons 100 "AcDbCircle")
          (list 10 -0.61523991 -0.16759131 0.00000000)
          (cons 40  0.00152400)
          (list 210 0.00000000 0.00000000 1.00000000)
          (cons 100 "AcDbArc")
          (cons 50  0.03489860)
          (cons 51  1.52084017)
         )
         (list
          (cons 0 "LINE")
          (cons 100 "AcDbEntity")
          (cons 67 0)
          (cons 8 "0")
          (cons 62 1)
          (cons 6 "Continuous")
          (cons 100 "AcDbLine")
          (list 10 -0.61523994 -0.21673376 0.00000000)
          (list 11 -0.61523994 -0.33173376 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.61600194 -0.33173376 0.00000000)
          (list 11 -0.61600194 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.60825480 -0.18704159 0.00000000)
          (list 11 -0.57952754 -0.18632340 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.60840298 -0.18625376 0.00000000)
          (list 11 -0.57479044 -0.18625376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.57904388 -0.18290860 0.00000000)
          (list 11 -0.61138275 -0.17302160 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.61518654 -0.16911991 0.00000000)
          (cons 40  0.00152400)
          (list 210 0.00000000 0.00000000 1.00000000)
          (cons 100 "AcDbArc")
          (cons 50  0.03489860)
          (cons 51  1.52083715)
         )
         (list
          (cons 0 "ARC")
          (cons 100 "AcDbEntity")
          (cons 67 0)
          (cons 8 "0")
          (cons 62 1)
          (cons 6 "Continuous")
          (cons 100 "AcDbCircle")
          (list 10 -0.61045447 -0.16998532 0.00000000)
          (cons 40  0.00317500)
          (list 210 0.00000000 0.00000000 1.00000000)
          (cons 100 "AcDbArc")
          (cons 50  3.17648866)
          (cons 51  4.41568060)
         )
         (list
          (cons 0 "ARC")
          (cons 100 "AcDbEntity")
          (cons 67 0)
          (cons 8 "0")
          (cons 62 1)
          (cons 6 "Continuous")
          (cons 100 "AcDbCircle")
          (list 10 -0.62259437 -0.18260976 0.00000000)
          (cons 40  0.00304800)
          (list 210 0.00000000 0.00000000 1.00000000)
          (cons 100 "AcDbArc")
          (cons 50  0.03489992)
          (cons 51  1.52083597)
         )
         (list
          (cons 0 "LINE")
          (cons 100 "AcDbEntity")
          (cons 67 0)
          (cons 8 "0")
          (cons 62 1)
          (cons 6 "Continuous")
          (cons 100 "AcDbLine")
          (list 10 -0.61954824 -0.18250345 0.00000000)
          (list 11 -0.61948195 -0.18440200 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62252809 -0.18450830 0.00000000)
          (cons 40  0.00304800)
          (list 210 0.00000000 0.00000000 1.00000000)
          (cons 100 "AcDbArc")
          (cons 50  4.71238932)
          (cons 51  0.03488134)
         )
         (list
          (cons 0 "LINE")
          (cons 100 "AcDbEntity")
          (cons 67 0)
          (cons 8 "0")
          (cons 62 1)
          (cons 6 "Continuous")
          (cons 100 "AcDbLine")
          (list 10 -0.61319847 -0.18238548 0.00000000)
          (list 11 -0.61371683 -0.16753814 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.60837541 -0.18221710 0.00000000)
          (cons 40  0.00482600)
          (list 210 0.00000000 0.00000000 1.00000000)
          (cons 100 "AcDbArc")
          (cons 50  3.17649126)
          (cons 51  4.73738391)
         )
         (list
          (cons 0 "ARC")
          (cons 100 "AcDbEntity")
          (cons 67 0)
          (cons 8 "0")
          (cons 62 1)
          (cons 100 "AcDbCircle")
          (list 10 -0.60840297 -0.18142776 0.00000000)
          (cons 40  0.00482600)
          (list 210 0.00000000 0.00000000 1.00000000)
          (cons 100 "AcDbArc")
          (cons 50  3.17518655)
          (cons 51  4.71369369)
         )
         (list
          (cons 0 "ARC")
          (cons 100 "AcDbEntity")
          (cons 67 0)
          (cons 8 "0")
          (cons 62 1)
          (cons 6 "Continuous")
          (cons 100 "AcDbCircle")
          (list 10 -0.56844044 -0.20174776 0.00000000)
          (cons 40  0.00635000)
          (list 210 0.00000000 0.00000000 1.00000000)
          (cons 100 "AcDbArc")
          (cons 50  3.14159265)
          (cons 51  4.71238898)
         )
         (list
          (cons 0 "LINE")
          (cons 100 "AcDbEntity")
          (cons 67 0)
          (cons 8 "0")
          (cons 62 1)
          (cons 6 "Continuous")
          (cons 100 "AcDbLine")
          (list 10 -0.57479044 -0.20174776 0.00000000)
          (list 11 -0.57479044 -0.18625376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.57948944 -0.19114998 0.00000000)
          (cons 40  0.00152400)
          (list 210 0.00000000 0.00000000 1.00000000)
          (cons 100 "AcDbArc")
          (cons 50  4.73738352)
          (cons 51  0.00000000)
         )
         (list
          (cons 0 "LINE")
          (cons 100 "AcDbEntity")
          (cons 67 0)
          (cons 8 "0")
          (cons 62 1)
          (cons 6 "Continuous")
          (cons 100 "AcDbLine")
          (list 10 -0.58245426 -0.18625376 0.00000000)
          (list 11 -0.58260074 -0.18640024 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.58357679 -0.18625376 0.00000000)
          (list 11 -0.58375205 -0.18642902 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.57948945 -0.18784694 0.00000000)
          (cons 40  0.00152401)
          (list 210 0.00000000 0.00000000 1.00000000)
          (cons 100 "AcDbArc")
          (cons 50  6.28317919)
          (cons 51  1.59579250)
         )
         (list
          (cons 0 "LINE")
          (cons 100 "AcDbEntity")
          (cons 67 0)
          (cons 8 "0")
          (cons 62 1)
          (cons 6 "Continuous")
          (cons 100 "AcDbLine")
          (list 10 -0.57796544 -0.18784695 0.00000000)
          (list 11 -0.57796544 -0.19114998 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.57796544 -0.18436603 0.00000000)
          (list 11 -0.57796544 -0.18628434 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.57948945 -0.18436602 0.00000000)
          (cons 40  0.00152401)
          (list 210 0.00000000 0.00000000 1.00000000)
          (cons 100 "AcDbArc")
          (cons 50  6.28317861)
          (cons 51  1.27409195)
         )
         (list
          (cons 0 "LINE")
          (cons 100 "AcDbEntity")
          (cons 67 0)
          (cons 8 "0")
          (cons 62 1)
          (cons 6 "Continuous")
          (cons 100 "AcDbLine")
          (list 10 -0.56723394 -0.20809776 0.00000000)
          (list 11 -0.56844044 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.56831344 -0.21673376 0.00000000)
          (list 11 -0.56831344 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.56723394 -0.21673376 0.00000000)
          (list 11 -0.56723394 -0.20809776 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62454631 -0.15708173 0.00000000)
          (cons 40  0.01003300)
          (list 210 0.00000000 0.00000000 1.00000000)
          (cons 100 "AcDbArc")
          (cons 50  5.22075529)
          (cons 51  6.08794592)
         )
         (list
          (cons 0 "LINE")
          (cons 100 "AcDbEntity")
          (cons 67 0)
          (cons 8 "0")
          (cons 62 1)
          (cons 6 "Continuous")
          (cons 100 "AcDbLine")
          (list 10 -0.61430444 -0.15449611 0.00000000)
          (list 11 -0.61470350 -0.15902636 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.64235280 -0.35066986 0.00000000)
          (list 11 0.64235280 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.63272909 -0.35066986 0.00000000)
          (list 11 0.63272909 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.61348168 -0.35066986 0.00000000)
          (list 11 0.61348168 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.60385798 -0.33885393 0.00000000)
          (list 11 0.60385798 -0.35066986 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89942909 -0.35066986 0.00000000)
          (list 11 0.89942909 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90905280 -0.33885393 0.00000000)
          (list 11 0.90905280 -0.35066986 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.88018168 -0.35066986 0.00000000)
          (list 11 0.88018168 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87055798 -0.35066986 0.00000000)
          (list 11 0.87055798 -0.33885393 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.62310539 -0.32459114 0.00000000)
          (cons 40  0.02779776)
          (list 210 0.00000000 0.00000000 1.00000000)
          (cons 100 "AcDbArc")
          (cons 50  4.35886680)
          (cons 51  5.06591116)
         )
         (list
          (cons 0 "LINE")
          (cons 100 "AcDbEntity")
          (cons 67 0)
          (cons 8 "0")
          (cons 62 1)
          (cons 6 "Continuous")
          (cons 100 "AcDbLine")
          (list 10 0.63754095 -0.35238896 0.00000000)
          (list 11 0.60866983 -0.35238896 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.60866983 -0.34479415 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 0.63754095 -0.34479415 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 0.88980539 -0.32459114 0.00000000)
          (cons 40  0.02779776)
          (list 210 0.00000000 0.00000000 1.00000000)
          (cons 100 "AcDbArc")
          (cons 50  4.35886680)
          (cons 51  5.06591116)
         )
         (list
          (cons 0 "LINE")
          (cons 100 "AcDbEntity")
          (cons 67 0)
          (cons 8 "0")
          (cons 62 1)
          (cons 6 "Continuous")
          (cons 100 "AcDbLine")
          (list 10 0.87536983 -0.35238896 0.00000000)
          (list 11 0.90424095 -0.35238896 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.87536983 -0.34479415 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 0.90424095 -0.34479415 0.00000000)
          (cons 40  0.00759460)
          (list 210 0.00000000 0.00000000 1.00000000)
          (cons 100 "AcDbArc")
          (cons 50  4.02620608)
          (cons 51  5.39857188)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 0.87230539 -0.21980747 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.54627039 -0.21980747 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "LINE")
          (cons 100 "AcDbEntity")
          (cons 67 0)
          (cons 8 "0")
          (cons 62 1)
          (cons 6 "Continuous")
          (cons 100 "AcDbLine")
          (list 10 0.82598601 -0.16491097 0.00000000)
          (list 11 0.68706940 -0.17185683 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.69106555 -0.21470993 0.00000000)
          (list 11 0.75645539 -0.21470993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.80547178 -0.18489752 0.00000000)
          (list 11 0.70743900 -0.18489752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.80342294 -0.18794552 0.00000000)
          (list 11 0.70948781 -0.18794552 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.75645539 -0.21661493 0.00000000)
          (list 11 0.56398689 -0.21661493 0.00000000)
          (list 210 0.00000000 0.00000000 1.00000000)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 0.76419986 -0.12944852 0.00000000)
          (cons 40  0.00000000)
          (cons 41  0.00000000)
          (cons 42  -0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.75910098 -0.05347330 0.00000000)
          (cons 40  0.00000000)
          (cons 41  0.00000000)
          (cons 42  -0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.77259902 -0.03601235 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.78201498 -0.03315233 0.00000000)
          (cons 40  0.00000000)
          (cons 41  0.00000000)
          (cons 42  0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.78314548 -0.03150154 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.78156758 -0.01049529 0.00000000)
          (cons 40  0.00000000)
          (cons 41  0.00000000)
          (cons 42  0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.77528156 -0.00224490 0.00000000)
          (cons 40  0.00000000)
          (cons 41  0.00000000)
          (cons 42  0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.76292523 -0.00002067 0.00000000)
          (cons 40  0.00000000)
          (cons 41  0.00000000)
          (cons 42  0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.74704524 -0.00031747 0.00000000)
          (cons 40  0.00000000)
          (cons 41  0.00000000)
          (cons 42  0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.73121484 -0.00160619 0.00000000)
          (cons 40  0.00000000)
          (cons 41  0.00000000)
          (cons 42  0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71914201 -0.00505188 0.00000000)
          (cons 40  0.00000000)
          (cons 41  0.00000000)
          (cons 42  0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71371033 -0.01388816 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71423569 -0.03494703 0.00000000)
          (cons 40  0.00000000)
          (cons 41  0.00000000)
          (cons 42  0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71552521 -0.03647682 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.72517949 -0.03838333 0.00000000)
          (cons 40  0.00000000)
          (cons 41  0.00000000)
          (cons 42  -0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.74035195 -0.05441075 0.00000000)
          (cons 40  0.00000000)
          (cons 41  0.00000000)
          (cons 42  -0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.74285708 -0.13051566 0.00000000)
          (cons 40  0.00000000)
          (cons 41  0.00000000)
          (cons 42  -0.30975875)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.72939626 -0.14732797 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68632615 -0.16041017 0.00000000)
          (cons 40  0.00000000)
          (cons 41  0.00000000)
          (cons 42  0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68519316 -0.16202101 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68560599 -0.17027766 0.00000000)
          (cons 40  0.00000000)
          (cons 41  0.00000000)
          (cons 42  0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68728390 -0.17179576 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.75544874 -0.16838752 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82361359 -0.16497927 0.00000000)
          (cons 40  0.00000000)
          (cons 41  0.00000000)
          (cons 42  0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82513169 -0.16330137 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82471886 -0.15504472 0.00000000)
          (cons 40  0.00000000)
          (cons 41  0.00000000)
          (cons 42  0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82343084 -0.15355494 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.77927059 -0.14483426 0.00000000)
          (cons 40  0.00000000)
          (cons 41  0.00000000)
          (cons 42  -0.30975875)
          (cons 91 0)
          (cons 70 0)
          (cons 50  0.00000000)
         )
         (list
          (cons 0 "SEQEND")
          (cons 100 "AcDbEntity")
          (cons 67 0)
          (cons 8 "0")
          (cons 62 1)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.59309019 -0.33161493 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.59309019 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.65312059 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.65312059 -0.33161493 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "ARC")
          (cons 100 "AcDbEntity")
          (cons 67 0)
          (cons 8 "0")
          (cons 62 1)
          (cons 6 "Continuous")
          (cons 100 "AcDbCircle")
          (list 10 0.65865480 -0.16339240 0.00000000)
          (cons 40  0.04795206)
          (list 210 0.00000000 0.00000000 1.00000000)
          (cons 100 "AcDbArc")
          (cons 50  1.58268281)
          (cons 51  2.79173224)
         )
         (list
          (cons 0 "ARC")
          (cons 100 "AcDbEntity")
          (cons 67 0)
          (cons 8 "0")
          (cons 62 1)
          (cons 100 "AcDbCircle")
          (list 10 0.62987989 -0.16187331 0.00000000)
          (cons 40  0.00317500)
          (list 210 0.00000000 0.00000000 1.00000000)
          (cons 100 "AcDbArc")
          (cons 50  4.76234514)
          (cons 51  6.06321256)
         )
         (list
          (cons 0 "ARC")
          (cons 100 "AcDbEntity")
          (cons 67 0)
          (cons 8 "0")
          (cons 62 1)
          (cons 100 "AcDbCircle")
          (list 10 0.62957955 -0.16341420 0.00000000)
          (cons 40  0.00317500)
          (list 210 0.00000000 0.00000000 1.00000000)
          (cons 100 "AcDbArc")
          (cons 50  4.76234816)
          (cons 51  6.11815870)
         )
         (list
          (cons 0 "ARC")
          (cons 100 "AcDbEntity")
          (cons 67 0)
          (cons 8 "0")
          (cons 62 1)
          (cons 100 "AcDbCircle")
          (list 10 0.62132441 -0.15696136 0.00000000)
          (cons 40  0.01003300)
          (list 210 0.00000000 0.00000000 1.00000000)
          (cons 100 "AcDbArc")
          (cons 50  5.32091457)
          (cons 51  6.18810520)
         )
         (list
          (cons 0 "ARC")
          (cons 100 "AcDbEntity")
          (cons 67 0)
          (cons 8 "0")
          (cons 62 1)
          (cons 100 "AcDbCircle")
          (list 10 0.62106561 -0.15366764 0.00000000)
          (cons 40  0.01003300)
          (list 210 0.00000000 0.00000000 1.00000000)
          (cons 100 "AcDbArc")
          (cons 50  6.27844057)
          (cons 51  3.21240381)
         )
         (list
          (cons 0 "LINE")
          (cons 100 "AcDbEntity")
          (cons 67 0)
          (cons 8 "0")
          (cons 62 1)
          (cons 6 "Continuous")
          (cons 100 "AcDbLine")
          (list 10 0.63316516 -0.17874828 0.00000000)
          (list 11 0.61919511 -0.17944678 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.65865475 -0.16339230 0.00000000)
          (cons 40  0.02788609)
          (list 210 0.00000000 0.00000000 1.00000000)
          (cons 100 "AcDbArc")
          (cons 50  1.37836689)
          (cons 51  2.94384873)
         )
         (list
          (cons 0 "LINE")
          (cons 100 "AcDbEntity")
          (cons 67 0)
          (cons 8 "0")
          (cons 62 1)
          (cons 6 "Continuous")
          (cons 100 "AcDbLine")
          (list 10 0.68501951 -0.19378752 0.00000000)
          (list 11 0.62551839 -0.19378752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.65804517 -0.18743752 0.00000000)
          (list 11 0.61928104 -0.18743752 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.61199285 -0.16747249 0.00000000)
          (cons 40  0.00152400)
          (list 210 0.00000000 0.00000000 1.00000000)
          (cons 100 "AcDbArc")
          (cons 50  1.62075249)
          (cons 51  3.10669405)
         )
         (list
          (cons 0 "LINE")
          (cons 100 "AcDbEntity")
          (cons 67 0)
          (cons 8 "0")
          (cons 62 1)
          (cons 6 "Continuous")
          (cons 100 "AcDbLine")
          (list 10 0.62973811 -0.16658524 0.00000000)
          (list 11 0.61186338 -0.16747899 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.56506639 -0.21026493 0.00000000)
          (list 11 0.62259739 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.56519339 -0.20162893 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 0.56398689 -0.21661493 0.00000000)
          (list 11 0.56398689 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.56506639 -0.21661493 0.00000000)
          (list 11 0.56506639 -0.21026493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.56398689 -0.20797893 0.00000000)
          (list 11 0.56519339 -0.20797893 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.61275489 -0.33161493 0.00000000)
          (list 11 0.61275489 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.61199289 -0.21661493 0.00000000)
          (list 11 0.61199289 -0.33161493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.60515592 -0.18613493 0.00000000)
          (list 11 0.57154339 -0.18613493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.60500774 -0.18692277 0.00000000)
          (list 11 0.57628049 -0.18620458 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57579682 -0.18278978 0.00000000)
          (list 11 0.60813570 -0.17290278 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.62551839 -0.19378752 0.00000000)
          (list 11 0.57620430 -0.19255468 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57154339 -0.20162893 0.00000000)
          (list 11 0.57154339 -0.18613493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.57624240 -0.18424720 0.00000000)
          (cons 40  0.00152401)
          (list 210 0.00000000 0.00000000 1.00000000)
          (cons 100 "AcDbArc")
          (cons 50  1.86750070)
          (cons 51  3.14159935)
         )
         (list
          (cons 0 "LINE")
          (cons 100 "AcDbEntity")
          (cons 67 0)
          (cons 8 "0")
          (cons 62 1)
          (cons 6 "Continuous")
          (cons 100 "AcDbLine")
          (list 10 0.57471839 -0.18424721 0.00000000)
          (list 11 0.57471839 -0.18616552 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57471839 -0.18772812 0.00000000)
          (list 11 0.57471839 -0.19103116 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.57624240 -0.18772811 0.00000000)
          (cons 40  0.00152401)
          (list 210 0.00000000 0.00000000 1.00000000)
          (cons 100 "AcDbArc")
          (cons 50  1.54580015)
          (cons 51  3.14159877)
         )
         (list
          (cons 0 "LINE")
          (cons 100 "AcDbEntity")
          (cons 67 0)
          (cons 8 "0")
          (cons 62 1)
          (cons 6 "Continuous")
          (cons 100 "AcDbLine")
          (list 10 0.58032973 -0.18613493 0.00000000)
          (list 11 0.58050499 -0.18631019 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57920720 -0.18613493 0.00000000)
          (list 11 0.57935369 -0.18628142 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.57624239 -0.19103116 0.00000000)
          (cons 40  0.00152400)
          (list 210 0.00000000 0.00000000 1.00000000)
          (cons 100 "AcDbArc")
          (cons 50  3.14159265)
          (cons 51  4.68739444)
         )
         (list
          (cons 0 "ARC")
          (cons 100 "AcDbEntity")
          (cons 67 0)
          (cons 8 "0")
          (cons 62 1)
          (cons 6 "Continuous")
          (cons 100 "AcDbCircle")
          (list 10 0.60720742 -0.16986650 0.00000000)
          (cons 40  0.00317500)
          (list 210 0.00000000 0.00000000 1.00000000)
          (cons 100 "AcDbArc")
          (cons 50  5.00909736)
          (cons 51  6.24828930)
         )
         (list
          (cons 0 "ARC")
          (cons 100 "AcDbEntity")
          (cons 67 0)
          (cons 8 "0")
          (cons 62 1)
          (cons 6 "Continuous")
          (cons 100 "AcDbCircle")
          (list 10 0.61193948 -0.16900109 0.00000000)
          (cons 40  0.00152400)
          (list 210 0.00000000 0.00000000 1.00000000)
          (cons 100 "AcDbArc")
          (cons 50  1.62075550)
          (cons 51  3.10669405)
         )
         (list
          (cons 0 "ARC")
          (cons 100 "AcDbEntity")
          (cons 67 0)
          (cons 8 "0")
          (cons 62 1)
          (cons 100 "AcDbCircle")
          (list 10 0.61928103 -0.18438947 0.00000000)
          (cons 40  0.00304800)
          (list 210 0.00000000 0.00000000 1.00000000)
          (cons 100 "AcDbArc")
          (cons 50  3.10671132)
          (cons 51  4.71238864)
         )
         (list
          (cons 0 "LINE")
          (cons 100 "AcDbEntity")
          (cons 67 0)
          (cons 8 "0")
          (cons 62 1)
          (cons 6 "Continuous")
          (cons 100 "AcDbLine")
          (list 10 0.61630119 -0.18238462 0.00000000)
          (list 11 0.61623489 -0.18428317 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.61934731 -0.18249094 0.00000000)
          (cons 40  0.00304800)
          (list 210 0.00000000 0.00000000 1.00000000)
          (cons 100 "AcDbArc")
          (cons 50  1.62075668)
          (cons 51  3.10669273)
         )
         (list
          (cons 0 "ARC")
          (cons 100 "AcDbEntity")
          (cons 67 0)
          (cons 8 "0")
          (cons 62 1)
          (cons 100 "AcDbCircle")
          (list 10 0.60515592 -0.18130894 0.00000000)
          (cons 40  0.00482600)
          (list 210 0.00000000 0.00000000 1.00000000)
          (cons 100 "AcDbArc")
          (cons 50  4.71108427)
          (cons 51  6.24959141)
         )
         (list
          (cons 0 "ARC")
          (cons 100 "AcDbEntity")
          (cons 67 0)
          (cons 8 "0")
          (cons 62 1)
          (cons 6 "Continuous")
          (cons 100 "AcDbCircle")
          (list 10 0.60512835 -0.18209827 0.00000000)
          (cons 40  0.00482600)
          (list 210 0.00000000 0.00000000 1.00000000)
          (cons 100 "AcDbArc")
          (cons 50  4.68739405)
          (cons 51  6.24828671)
         )
         (list
          (cons 0 "LINE")
          (cons 100 "AcDbEntity")
          (cons 67 0)
          (cons 8 "0")
          (cons 62 1)
          (cons 6 "Continuous")
          (cons 100 "AcDbLine")
          (list 10 0.60995141 -0.18226666 0.00000000)
          (list 11 0.61046978 -0.16741932 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.62259739 -0.21026493 0.00000000)
          (list 11 0.62259739 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.61105738 -0.15437729 0.00000000)
          (list 11 0.61145644 -0.15890753 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.62129926 -0.15696291 0.00000000)
          (cons 40  0.01003300)
          (list 210 0.00000000 0.00000000 1.00000000)
          (cons 100 "AcDbArc")
          (cons 50  3.33683204)
          (cons 51  4.20402267)
         )
         (list
          (cons 0 "LINE")
          (cons 100 "AcDbEntity")
          (cons 67 0)
          (cons 8 "0")
          (cons 62 1)
          (cons 6 "Continuous")
          (cons 100 "AcDbLine")
          (list 10 0.63003844 -0.16504435 0.00000000)
          (list 11 0.61191675 -0.16595039 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.65776634 -0.16810846 0.00000000)
          (cons 40  0.01308100)
          (list 210 0.00000000 0.00000000 1.00000000)
          (cons 100 "AcDbArc")
          (cons 50  5.75958633)
          (cons 51  2.61799368)
         )
         (list
          (cons 0 "CIRCLE")
          (cons 100 "AcDbEntity")
          (cons 67 0)
          (cons 8 "0")
          (cons 62 1)
          (cons 100 "AcDbCircle")
          (list 10 0.65790463 -0.16505957 0.00000000)
          (cons 40  0.01003300)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68547138 -0.17041449 0.00000000)
          (list 11 0.68522731 -0.16575700 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.64643785 -0.16156798 0.00000000)
          (list 11 0.63834732 -0.17558121 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.68501951 -0.20166152 0.00000000)
          (cons 40  0.00787400)
          (list 210 0.00000000 0.00000000 1.00000000)
          (cons 100 "AcDbArc")
          (cons 50  0.05235824)
          (cons 51  1.57079633)
         )
         (list
          (cons 0 "ARC")
          (cons 100 "AcDbEntity")
          (cons 67 0)
          (cons 8 "0")
          (cons 62 1)
          (cons 6 "Continuous")
          (cons 100 "AcDbCircle")
          (list 10 0.69500280 -0.21242393 0.00000000)
          (cons 40  0.00228600)
          (list 210 0.00000000 0.00000000 1.00000000)
          (cons 100 "AcDbArc")
          (cons 50  3.19395433)
          (cons 51  4.71238898)
         )
         (list
          (cons 0 "LINE")
          (cons 100 "AcDbEntity")
          (cons 67 0)
          (cons 8 "0")
          (cons 62 1)
          (cons 6 "Continuous")
          (cons 100 "AcDbLine")
          (list 10 0.63421789 -0.21661493 0.00000000)
          (list 11 0.63421789 -0.33161493 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.63345589 -0.33161493 0.00000000)
          (list 11 0.63345589 -0.21661493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.65804517 -0.18108749 0.00000000)
          (cons 40  0.00635000)
          (list 210 0.00000000 0.00000000 1.00000000)
          (cons 100 "AcDbArc")
          (cons 50  4.71238756)
          (cons 51  5.75958441)
         )
         (list
          (cons 0 "LINE")
          (cons 100 "AcDbEntity")
          (cons 67 0)
          (cons 8 "0")
          (cons 62 1)
          (cons 6 "Continuous")
          (cons 100 "AcDbLine")
          (list 10 0.63834539 -0.21026493 0.00000000)
          (list 11 0.67523889 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.63284811 -0.17240608 0.00000000)
          (cons 40  0.00635000)
          (list 210 0.00000000 0.00000000 1.00000000)
          (cons 100 "AcDbArc")
          (cons 50  4.76234930)
          (cons 51  5.75958792)
         )
         (list
          (cons 0 "LINE")
          (cons 100 "AcDbEntity")
          (cons 67 0)
          (cons 8 "0")
          (cons 62 1)
          (cons 6 "Continuous")
          (cons 100 "AcDbLine")
          (list 10 0.63834539 -0.21026493 0.00000000)
          (list 11 0.63834539 -0.21661493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.68699328 -0.17033466 0.00000000)
          (cons 40  0.00152400)
          (list 210 0.00000000 0.00000000 1.00000000)
          (cons 100 "AcDbArc")
          (cons 50  3.19394659)
          (cons 51  4.76234498)
         )
         (list
          (cons 0 "ARC")
          (cons 100 "AcDbEntity")
          (cons 67 0)
          (cons 8 "0")
          (cons 62 1)
          (cons 6 "Continuous")
          (cons 100 "AcDbCircle")
          (list 10 0.69111131 -0.20310692 0.00000000)
          (cons 40  0.00111252)
          (list 210 0.00000000 0.00000000 1.00000000)
          (cons 100 "AcDbArc")
          (cons 50  0.05236168)
          (cons 51  3.10668488)
         )
         (list
          (cons 0 "LINE")
          (cons 100 "AcDbEntity")
          (cons 67 0)
          (cons 8 "0")
          (cons 62 1)
          (cons 6 "Continuous")
          (cons 100 "AcDbLine")
          (list 10 0.68158889 -0.20137493 0.00000000)
          (list 11 0.68158889 -0.20391493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68527189 -0.20137493 0.00000000)
          (list 11 0.68158889 -0.20137493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68793889 -0.20404193 0.00000000)
          (list 11 0.68793889 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.68527189 -0.20404193 0.00000000)
          (cons 40  0.00266700)
          (list 210 0.00000000 0.00000000 1.00000000)
          (cons 100 "AcDbArc")
          (cons 50  0.00000000)
          (cons 51  1.57079633)
         )
         (list
          (cons 0 "LINE")
          (cons 100 "AcDbEntity")
          (cons 67 0)
          (cons 8 "0")
          (cons 62 1)
          (cons 100 "AcDbLine")
          (list 10 0.68954155 -0.21623393 0.00000000)
          (list 11 0.68954155 -0.21661493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.69106555 -0.21623393 0.00000000)
          (cons 40  0.00152400)
          (list 210 0.00000000 0.00000000 1.00000000)
          (cons 100 "AcDbArc")
          (cons 50  1.57079633)
          (cons 51  3.14159265)
         )
         (list
          (cons 0 "ARC")
          (cons 100 "AcDbEntity")
          (cons 67 0)
          (cons 8 "0")
          (cons 62 1)
          (cons 6 "Continuous")
          (cons 100 "AcDbCircle")
          (list 10 0.68158889 -0.21026493 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 0.69271993 -0.21254358 0.00000000)
          (list 11 0.69222231 -0.20304870 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68999947 -0.20306809 0.00000000)
          (list 11 0.68952639 -0.21661493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.67523889 -0.20391493 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 0.66909481 -0.17464898 0.00000000)
          (list 11 0.66354442 -0.18426252 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.70743900 -0.18807251 0.00000000)
          (cons 40  0.00317500)
          (list 210 0.00000000 0.00000000 1.00000000)
          (cons 100 "AcDbArc")
          (cons 50  1.57079752)
          (cons 51  3.08923406)
         )
         (list
          (cons 0 "ARC")
          (cons 100 "AcDbEntity")
          (cons 67 0)
          (cons 8 "0")
          (cons 62 1)
          (cons 100 "AcDbCircle")
          (list 10 0.70374651 -0.21242393 0.00000000)
          (cons 40  0.00228600)
          (list 210 0.00000000 0.00000000 1.00000000)
          (cons 100 "AcDbArc")
          (cons 50  4.71238898)
          (cons 51  6.23082684)
         )
         (list
          (cons 0 "LINE")
          (cons 100 "AcDbEntity")
          (cons 67 0)
          (cons 8 "0")
          (cons 62 1)
          (cons 6 "Continuous")
          (cons 100 "AcDbLine")
          (list 10 0.70154217 -0.21232952 0.00000000)
          (list 11 0.69490961 -0.21232952 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.69338770 -0.21088528 0.00000000)
          (list 11 0.69288272 -0.20124944 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.70154217 -0.21080552 0.00000000)
          (cons 40  0.00152400)
          (list 210 0.00000000 0.00000000 1.00000000)
          (cons 100 "AcDbArc")
          (cons 50  4.71238898)
          (cons 51  6.23082584)
         )
         (list
          (cons 0 "LINE")
          (cons 100 "AcDbEntity")
          (cons 67 0)
          (cons 8 "0")
          (cons 62 1)
          (cons 6 "Continuous")
          (cons 100 "AcDbLine")
          (list 10 0.70306408 -0.21088528 0.00000000)
          (list 11 0.70426835 -0.18790636 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.69490961 -0.21080552 0.00000000)
          (cons 40  0.00152400)
          (list 210 0.00000000 0.00000000 1.00000000)
          (cons 100 "AcDbArc")
          (cons 50  3.19395089)
          (cons 51  4.71238898)
         )
         (list
          (cons 0 "ARC")
          (cons 100 "AcDbEntity")
          (cons 67 0)
          (cons 8 "0")
          (cons 62 1)
          (cons 6 "Continuous")
          (cons 100 "AcDbCircle")
          (list 10 0.70948781 -0.19023152 0.00000000)
          (cons 40  0.00228600)
          (list 210 0.00000000 0.00000000 1.00000000)
          (cons 100 "AcDbArc")
          (cons 50  1.57079633)
          (cons 51  3.08923419)
         )
         (list
          (cons 0 "LINE")
          (cons 100 "AcDbEntity")
          (cons 67 0)
          (cons 8 "0")
          (cons 62 1)
          (cons 6 "Continuous")
          (cons 100 "AcDbLine")
          (list 10 0.70602938 -0.21254357 0.00000000)
          (list 11 0.70720494 -0.19011189 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.65878123 -0.17258911 0.00000000)
          (cons 40  0.05715000)
          (list 210 0.00000000 0.00000000 1.00000000)
          (cons 100 "AcDbArc")
          (cons 50  0.57211891)
          (cons 51  1.58298294)
         )
         (list
          (cons 0 "LINE")
          (cons 100 "AcDbEntity")
          (cons 67 0)
          (cons 8 "0")
          (cons 62 1)
          (cons 6 "Continuous")
          (cons 100 "AcDbLine")
          (list 10 0.69060729 -0.15749575 0.00000000)
          (list 11 0.71120224 -0.15150935 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68991805 -0.14579288 0.00000000)
          (list 11 0.70430932 -0.14161003 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.69425588 -0.15140957 0.00000000)
          (cons 40  0.00709676)
          (list 210 0.00000000 0.00000000 1.00000000)
          (cons 100 "AcDbArc")
          (cons 50  2.22842372)
          (cons 51  4.61698351)
         )
         (list
          (cons 0 "ARC")
          (cons 100 "AcDbEntity")
          (cons 67 0)
          (cons 8 "0")
          (cons 62 1)
          (cons 100 "AcDbCircle")
          (list 10 0.65776634 -0.16810846 0.00000000)
          (cons 40  0.02540001)
          (list 210 0.00000000 0.00000000 1.00000000)
          (cons 100 "AcDbArc")
          (cons 50  0.31756105)
          (cons 51  2.97656605)
         )
         (list
          (cons 0 "LINE")
          (cons 100 "AcDbEntity")
          (cons 67 0)
          (cons 8 "0")
          (cons 62 1)
          (cons 6 "Continuous")
          (cons 100 "AcDbLine")
          (list 10 0.63109428 -0.15337272 0.00000000)
          (list 11 0.63116276 -0.15892807 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.69251355 -0.15668763 0.00000000)
          (cons 40  0.01117600)
          (list 210 0.00000000 0.00000000 1.00000000)
          (cons 100 "AcDbArc")
          (cons 50  3.45914932)
          (cons 51  3.94597282)
         )
         (list
          (cons 0 "ARC")
          (cons 100 "AcDbEntity")
          (cons 67 0)
          (cons 8 "0")
          (cons 62 1)
          (cons 6 "Continuous")
          (cons 100 "AcDbCircle")
          (list 10 0.68370540 -0.16583676 0.00000000)
          (cons 40  0.00152400)
          (list 210 0.00000000 0.00000000 1.00000000)
          (cons 100 "AcDbArc")
          (cons 50  0.05237527)
          (cons 51  0.80439198)
         )
         (list
          (cons 0 "ARC")
          (cons 100 "AcDbEntity")
          (cons 67 0)
          (cons 8 "0")
          (cons 62 1)
          (cons 100 "AcDbCircle")
          (list 10 0.65689584 -0.17242039 0.00000000)
          (cons 40  0.03708400)
          (list 210 0.00000000 0.00000000 1.00000000)
          (cons 100 "AcDbArc")
          (cons 50  0.61563997)
          (cons 51  1.37836895)
         )
         (list
          (cons 0 "ARC")
          (cons 100 "AcDbEntity")
          (cons 67 0)
          (cons 8 "0")
          (cons 62 1)
          (cons 6 "Continuous")
          (cons 100 "AcDbCircle")
          (list 10 0.70547342 -0.14814883 0.00000000)
          (cons 40  0.00664164)
          (list 210 0.00000000 0.00000000 1.00000000)
          (cons 100 "AcDbArc")
          (cons 50  5.25931137)
          (cons 51  1.74699270)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.91982059 -0.33161493 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.91982059 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.85979019 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.85979019 -0.33161493 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "LINE")
          (cons 100 "AcDbEntity")
          (cons 67 0)
          (cons 8 "0")
          (cons 62 1)
          (cons 6 "Continuous")
          (cons 100 "AcDbLine")
          (list 10 0.94892389 -0.21661493 0.00000000)
          (list 11 0.75645539 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90982059 -0.20073993 0.00000000)
          (list 11 0.86979019 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.85005439 -0.20797893 0.00000000)
          (list 11 0.94892389 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90982059 -0.20797893 0.00000000)
          (list 11 0.86979019 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.83767189 -0.21026493 0.00000000)
          (list 11 0.94784439 -0.21026493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.89122805 -0.14499137 0.00000000)
          (cons 40  0.01003300)
          (list 210 0.00000000 0.00000000 1.00000000)
          (cons 100 "AcDbArc")
          (cons 50  3.38794173)
          (cons 51  4.20388555)
         )
         (list
          (cons 0 "ARC")
          (cons 100 "AcDbEntity")
          (cons 67 0)
          (cons 8 "0")
          (cons 62 1)
          (cons 100 "AcDbCircle")
          (list 10 0.85430384 -0.15361429 0.00000000)
          (cons 40  0.02788666)
          (list 210 0.00000000 0.00000000 1.00000000)
          (cons 100 "AcDbArc")
          (cons 50  0.22332772)
          (cons 51  0.66810518)
         )
         (list
          (cons 0 "ARC")
          (cons 100 "AcDbEntity")
          (cons 67 0)
          (cons 8 "0")
          (cons 62 1)
          (cons 6 "Continuous")
          (cons 100 "AcDbCircle")
          (list 10 0.88220234 -0.15078302 0.00000000)
          (cons 40  0.00317500)
          (list 210 0.00000000 0.00000000 1.00000000)
          (cons 100 "AcDbArc")
          (cons 50  3.40653662)
          (cons 51  4.76234402)
         )
         (list
          (cons 0 "ARC")
          (cons 100 "AcDbEntity")
          (cons 67 0)
          (cons 8 "0")
          (cons 62 1)
          (cons 6 "Continuous")
          (cons 100 "AcDbCircle")
          (list 10 0.88256789 -0.15229066 0.00000000)
          (cons 40  0.00317500)
          (list 210 0.00000000 0.00000000 1.00000000)
          (cons 100 "AcDbArc")
          (cons 50  3.35223205)
          (cons 51  4.76236200)
         )
         (list
          (cons 0 "LINE")
          (cons 100 "AcDbEntity")
          (cons 67 0)
          (cons 8 "0")
          (cons 62 1)
          (cons 6 "Continuous")
          (cons 100 "AcDbLine")
          (list 10 0.89280813 -0.16729199 0.00000000)
          (list 11 0.87931773 -0.16796652 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.90091789 -0.17031082 0.00000000)
          (list 11 0.87869289 -0.17031082 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87536983 -0.18720491 0.00000000)
          (list 11 0.90424095 -0.18720491 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.88980539 -0.21500273 0.00000000)
          (cons 40  0.02779776)
          (list 210 0.00000000 0.00000000 1.00000000)
          (cons 100 "AcDbArc")
          (cons 50  1.21727415)
          (cons 51  1.92431851)
         )
         (list
          (cons 0 "ARC")
          (cons 100 "AcDbEntity")
          (cons 67 0)
          (cons 8 "0")
          (cons 62 1)
          (cons 100 "AcDbCircle")
          (list 10 0.85430396 -0.15361449 0.00000000)
          (cons 40  0.04795266)
          (list 210 0.00000000 0.00000000 1.00000000)
          (cons 100 "AcDbArc")
          (cons 50  0.27024809)
          (cons 51  1.68983637)
         )
         (list
          (cons 0 "ARC")
          (cons 100 "AcDbEntity")
          (cons 67 0)
          (cons 8 "0")
          (cons 62 1)
          (cons 6 "Continuous")
          (cons 100 "AcDbCircle")
          (list 10 0.87900063 -0.16162444 0.00000000)
          (cons 40  0.00635001)
          (list 210 0.00000000 0.00000000 1.00000000)
          (cons 100 "AcDbArc")
          (cons 50  3.66518929)
          (cons 51  4.76234710)
         )
         (list
          (cons 0 "LINE")
          (cons 100 "AcDbEntity")
          (cons 67 0)
          (cons 8 "0")
          (cons 62 1)
          (cons 6 "Continuous")
          (cons 100 "AcDbLine")
          (list 10 0.84383139 -0.20162893 0.00000000)
          (list 11 0.84383139 -0.16573350 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.84011118 -0.15869308 0.00000000)
          (list 11 0.84128161 -0.19221034 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.84329591 -0.16480602 0.00000000)
          (list 11 0.85452911 -0.18426252 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82184616 -0.21470993 0.00000000)
          (list 11 0.75645539 -0.21470993 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.81790801 -0.21242327 0.00000000)
          (cons 40  0.00228600)
          (list 210 0.00000000 0.00000000 1.00000000)
          (cons 100 "AcDbArc")
          (cons 50  4.71239007)
          (cons 51  6.23084044)
         )
         (list
          (cons 0 "ARC")
          (cons 100 "AcDbEntity")
          (cons 67 0)
          (cons 8 "0")
          (cons 62 1)
          (cons 6 "Continuous")
          (cons 100 "AcDbCircle")
          (list 10 0.81800117 -0.21080552 0.00000000)
          (cons 40  0.00152400)
          (list 210 0.00000000 0.00000000 1.00000000)
          (cons 100 "AcDbArc")
          (cons 50  4.71239106)
          (cons 51  6.23083033)
         )
         (list
          (cons 0 "ARC")
          (cons 100 "AcDbEntity")
          (cons 67 0)
          (cons 8 "0")
          (cons 62 1)
          (cons 6 "Continuous")
          (cons 100 "AcDbCircle")
          (list 10 0.80547178 -0.18807253 0.00000000)
          (cons 40  0.00317500)
          (list 210 0.00000000 0.00000000 1.00000000)
          (cons 100 "AcDbArc")
          (cons 50  0.05236109)
          (cons 51  1.57079763)
         )
         (list
          (cons 0 "ARC")
          (cons 100 "AcDbEntity")
          (cons 67 0)
          (cons 8 "0")
          (cons 62 1)
          (cons 6 "Continuous")
          (cons 100 "AcDbCircle")
          (list 10 0.80342294 -0.19023152 0.00000000)
          (cons 40  0.00228600)
          (list 210 0.00000000 0.00000000 1.00000000)
          (cons 100 "AcDbArc")
          (cons 50  0.05235960)
          (cons 51  1.57079633)
         )
         (list
          (cons 0 "LINE")
          (cons 100 "AcDbEntity")
          (cons 67 0)
          (cons 8 "0")
          (cons 62 1)
          (cons 6 "Continuous")
          (cons 100 "AcDbLine")
          (list 10 0.81800116 -0.21232952 0.00000000)
          (list 11 0.81136861 -0.21232952 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.81136861 -0.21080552 0.00000000)
          (cons 40  0.00152400)
          (list 210 0.00000000 0.00000000 1.00000000)
          (cons 100 "AcDbArc")
          (cons 50  3.19395164)
          (cons 51  4.71239091)
         )
         (list
          (cons 0 "ARC")
          (cons 100 "AcDbEntity")
          (cons 67 0)
          (cons 8 "0")
          (cons 62 1)
          (cons 6 "Continuous")
          (cons 100 "AcDbCircle")
          (list 10 0.80916427 -0.21242393 0.00000000)
          (cons 40  0.00228600)
          (list 210 0.00000000 0.00000000 1.00000000)
          (cons 100 "AcDbArc")
          (cons 50  3.19395164)
          (cons 51  4.71239091)
         )
         (list
          (cons 0 "LINE")
          (cons 100 "AcDbEntity")
          (cons 67 0)
          (cons 8 "0")
          (cons 62 1)
          (cons 6 "Continuous")
          (cons 100 "AcDbLine")
          (list 10 0.80688140 -0.21254357 0.00000000)
          (list 11 0.80570581 -0.19011188 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.80984670 -0.21088528 0.00000000)
          (list 11 0.80864243 -0.18790636 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.87945489 -0.33161493 0.00000000)
          (list 11 0.87945489 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87869289 -0.21661493 0.00000000)
          (list 11 0.87869289 -0.33161493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.85018139 -0.20162893 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 6 "Continuous")
          (cons 100 "AcDbCircle")
          (list 10 0.82789129 -0.20166171 0.00000000)
          (cons 40  0.00787400)
          (list 210 0.00000000 0.00000000 1.00000000)
          (cons 100 "AcDbArc")
          (cons 50  1.57079658)
          (cons 51  3.08923025)
         )
         (list
          (cons 0 "ARC")
          (cons 100 "AcDbEntity")
          (cons 67 0)
          (cons 8 "0")
          (cons 62 1)
          (cons 100 "AcDbCircle")
          (list 10 0.83132189 -0.21026493 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 6 "Continuous")
          (cons 100 "AcDbCircle")
          (list 10 0.82763889 -0.20404193 0.00000000)
          (cons 40  0.00266700)
          (list 210 0.00000000 0.00000000 1.00000000)
          (cons 100 "AcDbArc")
          (cons 50  1.57079633)
          (cons 51  3.14159265)
         )
         (list
          (cons 0 "ARC")
          (cons 100 "AcDbEntity")
          (cons 67 0)
          (cons 8 "0")
          (cons 62 1)
          (cons 6 "Continuous")
          (cons 100 "AcDbCircle")
          (list 10 0.82179946 -0.20310692 0.00000000)
          (cons 40  0.00111252)
          (list 210 0.00000000 0.00000000 1.00000000)
          (cons 100 "AcDbArc")
          (cons 50  0.03490778)
          (cons 51  3.08923097)
         )
         (list
          (cons 0 "ARC")
          (cons 100 "AcDbEntity")
          (cons 67 0)
          (cons 8 "0")
          (cons 62 1)
          (cons 6 "Continuous")
          (cons 100 "AcDbCircle")
          (list 10 0.82184616 -0.21623393 0.00000000)
          (cons 40  0.00152399)
          (list 210 0.00000000 0.00000000 1.00000000)
          (cons 100 "AcDbArc")
          (cons 50  0.03490348)
          (cons 51  1.57079246)
         )
         (list
          (cons 0 "LINE")
          (cons 100 "AcDbEntity")
          (cons 67 0)
          (cons 8 "0")
          (cons 62 1)
          (cons 6 "Continuous")
          (cons 100 "AcDbLine")
          (list 10 0.81952308 -0.21088528 0.00000000)
          (list 11 0.82002806 -0.20124943 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82019085 -0.21254357 0.00000000)
          (list 11 0.82068847 -0.20304870 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82291131 -0.20306809 0.00000000)
          (list 11 0.82338439 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.83132189 -0.20137493 0.00000000)
          (list 11 0.83132189 -0.20391493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.83132189 -0.20137493 0.00000000)
          (list 11 0.82763889 -0.20137493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.83975854 -0.19226352 0.00000000)
          (cons 40  0.00152400)
          (list 210 0.00000000 0.00000000 1.00000000)
          (cons 100 "AcDbArc")
          (cons 50  4.71238898)
          (cons 51  0.03490610)
         )
         (list
          (cons 0 "LINE")
          (cons 100 "AcDbEntity")
          (cons 67 0)
          (cons 8 "0")
          (cons 62 1)
          (cons 6 "Continuous")
          (cons 100 "AcDbLine")
          (list 10 0.83975854 -0.19378752 0.00000000)
          (list 11 0.82789129 -0.19378752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82497189 -0.20404193 0.00000000)
          (list 11 0.82497189 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.83767189 -0.20391493 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 100 "AcDbCircle")
          (list 10 0.87536983 -0.19479972 0.00000000)
          (cons 40  0.00759460)
          (list 210 0.00000000 0.00000000 1.00000000)
          (cons 100 "AcDbArc")
          (cons 50  0.88461343)
          (cons 51  2.25697923)
         )
         (list
          (cons 0 "ARC")
          (cons 100 "AcDbEntity")
          (cons 67 0)
          (cons 8 "0")
          (cons 62 1)
          (cons 6 "Continuous")
          (cons 100 "AcDbCircle")
          (list 10 0.86002837 -0.18108751 0.00000000)
          (cons 40  0.00635001)
          (list 210 0.00000000 0.00000000 1.00000000)
          (cons 100 "AcDbArc")
          (cons 50  3.66519208)
          (cons 51  4.71239093)
         )
         (list
          (cons 0 "LINE")
          (cons 100 "AcDbEntity")
          (cons 67 0)
          (cons 8 "0")
          (cons 62 1)
          (cons 6 "Continuous")
          (cons 100 "AcDbLine")
          (list 10 0.87055798 -0.18743752 0.00000000)
          (list 11 0.86002838 -0.18743752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87055798 -0.18892401 0.00000000)
          (list 11 0.87055798 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.86188810 -0.21026493 0.00000000)
          (list 11 0.86188810 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.85488039 -0.21026493 0.00000000)
          (list 11 0.85488039 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.85005439 -0.20797766 0.00000000)
          (list 11 0.85005439 -0.21026493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.86979019 -0.20073993 0.00000000)
          (list 11 0.86979019 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.88018168 -0.18892401 0.00000000)
          (list 11 0.88018168 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87869289 -0.17031082 0.00000000)
          (list 11 0.87869289 -0.18720491 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.87945489 -0.18720491 0.00000000)
          (list 11 0.87945489 -0.17031082 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.85537964 -0.16274952 0.00000000)
          (cons 40  0.05715000)
          (list 210 0.00000000 0.00000000 1.00000000)
          (cons 100 "AcDbArc")
          (cons 50  1.68955122)
          (cons 51  2.74425538)
         )
         (list
          (cons 0 "ARC")
          (cons 100 "AcDbEntity")
          (cons 67 0)
          (cons 8 "0")
          (cons 62 1)
          (cons 100 "AcDbCircle")
          (list 10 0.80741348 -0.14343886 0.00000000)
          (cons 40  0.00664210)
          (list 210 0.00000000 0.00000000 1.00000000)
          (cons 100 "AcDbArc")
          (cons 50  2.11288665)
          (cons 51  4.40122392)
         )
         (list
          (cons 0 "ARC")
          (cons 100 "AcDbEntity")
          (cons 67 0)
          (cons 8 "0")
          (cons 62 1)
          (cons 100 "AcDbCircle")
          (list 10 0.85462441 -0.15826551 0.00000000)
          (cons 40  0.02540000)
          (list 210 0.00000000 0.00000000 1.00000000)
          (cons 100 "AcDbArc")
          (cons 50  0.26494369)
          (cons 51  2.96093612)
         )
         (list
          (cons 0 "ARC")
          (cons 100 "AcDbEntity")
          (cons 67 0)
          (cons 8 "0")
          (cons 62 1)
          (cons 100 "AcDbCircle")
          (list 10 0.85430391 -0.15361452 0.00000000)
          (cons 40  0.02788666)
          (list 210 0.00000000 0.00000000 1.00000000)
          (cons 100 "AcDbArc")
          (cons 50  0.66810459)
          (cons 51  1.89415366)
         )
         (list
          (cons 0 "ARC")
          (cons 100 "AcDbEntity")
          (cons 67 0)
          (cons 8 "0")
          (cons 62 1)
          (cons 6 "Continuous")
          (cons 100 "AcDbCircle")
          (list 10 0.85462440 -0.15826551 0.00000000)
          (cons 40  0.01308100)
          (list 210 0.00000000 0.00000000 1.00000000)
          (cons 100 "AcDbArc")
          (cons 50  0.52359898)
          (cons 51  3.66519163)
         )
         (list
          (cons 0 "ARC")
          (cons 100 "AcDbEntity")
          (cons 67 0)
          (cons 8 "0")
          (cons 62 1)
          (cons 100 "AcDbCircle")
          (list 10 0.85462438 -0.15302720 0.00000000)
          (cons 40  0.01008126)
          (list 210 0.00000000 0.00000000 1.00000000)
          (cons 100 "AcDbArc")
          (cons 50  0.40917396)
          (cons 51  2.73241933)
         )
         (list
          (cons 0 "CIRCLE")
          (cons 100 "AcDbEntity")
          (cons 67 0)
          (cons 8 "0")
          (cons 62 1)
          (cons 100 "AcDbCircle")
          (list 10 0.85481283 -0.15521891 0.00000000)
          (cons 40  0.01003300)
          (list 210 0.00000000 0.00000000 1.00000000)
         )
         (list
          (cons 0 "ARC")
          (cons 100 "AcDbEntity")
          (cons 67 0)
          (cons 8 "0")
          (cons 62 1)
          (cons 100 "AcDbCircle")
          (list 10 0.85722691 -0.16233550 0.00000000)
          (cons 40  0.03708400)
          (list 210 0.00000000 0.00000000 1.00000000)
          (cons 100 "AcDbArc")
          (cons 50  1.89416688)
          (cons 51  2.66089606)
         )
         (list
          (cons 0 "ARC")
          (cons 100 "AcDbEntity")
          (cons 67 0)
          (cons 8 "0")
          (cons 62 1)
          (cons 6 "Continuous")
          (cons 100 "AcDbCircle")
          (list 10 0.81887093 -0.14571570 0.00000000)
          (cons 40  0.00709647)
          (list 210 0.00000000 0.00000000 1.00000000)
          (cons 100 "AcDbArc")
          (cons 50  4.90386054)
          (cons 51  0.36939896)
         )
         (list
          (cons 0 "ARC")
          (cons 100 "AcDbEntity")
          (cons 67 0)
          (cons 8 "0")
          (cons 62 1)
          (cons 6 "Continuous")
          (cons 100 "AcDbCircle")
          (list 10 0.82590989 -0.16338886 0.00000000)
          (cons 40  0.00152400)
          (list 210 0.00000000 0.00000000 1.00000000)
          (cons 100 "AcDbArc")
          (cons 50  4.76235952)
          (cons 51  6.23082712)
         )
         (list
          (cons 0 "LINE")
          (cons 100 "AcDbEntity")
          (cons 67 0)
          (cons 8 "0")
          (cons 62 1)
          (cons 6 "Continuous")
          (cons 100 "AcDbLine")
          (list 10 0.82743180 -0.16346863 0.00000000)
          (list 11 0.82768347 -0.15866651 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.82920538 -0.15874627 0.00000000)
          (cons 40  0.00152400)
          (list 210 0.00000000 0.00000000 1.00000000)
          (cons 100 "AcDbArc")
          (cons 50  1.57079220)
          (cons 51  3.08923426)
         )
         (list
          (cons 0 "ARC")
          (cons 100 "AcDbEntity")
          (cons 67 0)
          (cons 8 "0")
          (cons 62 1)
          (cons 6 "Continuous")
          (cons 100 "AcDbCircle")
          (list 10 0.83858811 -0.15874626 0.00000000)
          (cons 40  0.00152399)
          (list 210 0.00000000 0.00000000 1.00000000)
          (cons 100 "AcDbArc")
          (cons 50  0.03490348)
          (cons 51  1.57079246)
         )
         (list
          (cons 0 "LINE")
          (cons 100 "AcDbEntity")
          (cons 67 0)
          (cons 8 "0")
          (cons 62 1)
          (cons 6 "Continuous")
          (cons 100 "AcDbLine")
          (list 10 0.84158506 -0.15722227 0.00000000)
          (list 11 0.82920538 -0.15722227 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.84158506 -0.15722227 0.00000000)
          (list 11 0.82920538 -0.15722227 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.81864363 -0.15169362 0.00000000)
          (cons 40  0.01117600)
          (list 210 0.00000000 0.00000000 1.00000000)
          (cons 100 "AcDbArc")
          (cons 50  5.69443002)
          (cons 51  6.10252135)
         )
         (list
          (cons 0 "LINE")
          (cons 100 "AcDbEntity")
          (cons 67 0)
          (cons 8 "0")
          (cons 62 1)
          (cons 6 "Continuous")
          (cons 100 "AcDbLine")
          (list 10 0.82747638 -0.16261806 0.00000000)
          (list 11 0.83287215 -0.15722227 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.86595286 -0.15172502 0.00000000)
          (list 11 0.87350136 -0.16479944 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.87025699 -0.15918003 0.00000000)
          (list 11 0.85899105 -0.16434049 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.87500755 -0.13493306 0.00000000)
          (list 11 0.86931135 -0.13754224 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.90533009 -0.16429228 0.00000000)
          (cons 40  0.00317500)
          (list 210 0.00000000 0.00000000 1.00000000)
          (cons 100 "AcDbArc")
          (cons 50  3.17649516)
          (cons 51  4.27604392)
         )
         (list
          (cons 0 "ARC")
          (cons 100 "AcDbEntity")
          (cons 67 0)
          (cons 8 "0")
          (cons 62 1)
          (cons 100 "AcDbCircle")
          (list 10 0.89296037 -0.17033727 0.00000000)
          (cons 40  0.00304800)
          (list 210 0.00000000 0.00000000 1.00000000)
          (cons 100 "AcDbArc")
          (cons 50  0.03525777)
          (cons 51  1.62074685)
         )
         (list
          (cons 0 "LINE")
          (cons 100 "AcDbEntity")
          (cons 67 0)
          (cons 8 "0")
          (cons 62 1)
          (cons 6 "Continuous")
          (cons 100 "AcDbLine")
          (list 10 0.90181212 -0.15453037 0.00000000)
          (list 11 0.90291574 -0.18613493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.94771739 -0.20162893 0.00000000)
          (cons 40  0.00635000)
          (list 210 0.00000000 0.00000000 1.00000000)
          (cons 100 "AcDbArc")
          (cons 50  3.14159265)
          (cons 51  4.71238898)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 0.96664039 -0.21980747 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.90730539 -0.21980747 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "LINE")
          (cons 100 "AcDbEntity")
          (cons 67 0)
          (cons 8 "0")
          (cons 62 1)
          (cons 6 "DASHED")
          (cons 100 "AcDbLine")
          (list 10 0.90015589 -0.33161493 0.00000000)
          (list 11 0.90015589 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90091789 -0.21661493 0.00000000)
          (list 11 0.90091789 -0.33161493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94136739 -0.18613493 0.00000000)
          (list 11 0.90091789 -0.18613493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.93731246 -0.18270921 0.00000000)
          (list 11 0.90398811 -0.16716980 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89600647 -0.17022983 0.00000000)
          (list 11 0.89600930 -0.17031082 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89942909 -0.18892401 0.00000000)
          (list 11 0.89942909 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90905280 -0.20073993 0.00000000)
          (list 11 0.90905280 -0.18892401 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.90424095 -0.19479972 0.00000000)
          (cons 40  0.00759460)
          (list 210 0.00000000 0.00000000 1.00000000)
          (cons 100 "AcDbArc")
          (cons 50  0.88461343)
          (cons 51  2.25697923)
         )
         (list
          (cons 0 "LINE")
          (cons 100 "AcDbEntity")
          (cons 67 0)
          (cons 8 "0")
          (cons 62 1)
          (cons 6 "Continuous")
          (cons 100 "AcDbLine")
          (list 10 0.90091789 -0.17031082 0.00000000)
          (list 11 0.90091789 -0.18720491 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.90015589 -0.18720491 0.00000000)
          (list 11 0.90015589 -0.17031082 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90982059 -0.20073993 0.00000000)
          (list 11 0.90982059 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89450253 -0.20797893 0.00000000)
          (list 11 0.88726353 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89234724 -0.20797893 0.00000000)
          (list 11 0.88510824 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94136739 -0.20162893 0.00000000)
          (list 11 0.94136739 -0.18613493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.93819239 -0.18409041 0.00000000)
          (list 11 0.93819239 -0.18613493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.93666839 -0.18409042 0.00000000)
          (cons 40  0.00152400)
          (list 210 0.00000000 0.00000000 1.00000000)
          (cons 100 "AcDbArc")
          (cons 50  0.00000668)
          (cons 51  1.13446471)
         )
         (list
          (cons 0 "LINE")
          (cons 100 "AcDbEntity")
          (cons 67 0)
          (cons 8 "0")
          (cons 62 1)
          (cons 6 "Continuous")
          (cons 100 "AcDbLine")
          (list 10 0.91772268 -0.21026493 0.00000000)
          (list 11 0.91772268 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.92473039 -0.21026493 0.00000000)
          (list 11 0.92473039 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.92955639 -0.20797893 0.00000000)
          (list 11 0.92955639 -0.21026493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94892389 -0.21661493 0.00000000)
          (list 11 0.94892389 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94869186 -0.21661493 0.00000000)
          (list 11 0.94784439 -0.21576746 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94784439 -0.21661493 0.00000000)
          (list 11 0.94784439 -0.21026493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.89122805 -0.14499137 0.00000000)
          (cons 40  0.01003300)
          (list 210 0.00000000 0.00000000 1.00000000)
          (cons 100 "AcDbArc")
          (cons 50  5.32080678)
          (cons 51  0.21754705)
         )
         (list
          (cons 0 "ARC")
          (cons 100 "AcDbEntity")
          (cons 67 0)
          (cons 8 "0")
          (cons 62 1)
          (cons 6 "Continuous")
          (cons 100 "AcDbCircle")
          (list 10 0.90034257 -0.15610679 0.00000000)
          (cons 40  0.00152400)
          (list 210 0.00000000 0.00000000 1.00000000)
          (cons 100 "AcDbArc")
          (cons 50  0.03490194)
          (cons 51  1.62078222)
         )
         (list
          (cons 0 "ARC")
          (cons 100 "AcDbEntity")
          (cons 67 0)
          (cons 8 "0")
          (cons 62 1)
          (cons 100 "AcDbCircle")
          (list 10 0.90028905 -0.15458361 0.00000000)
          (cons 40  0.00152400)
          (list 210 0.00000000 0.00000000 1.00000000)
          (cons 100 "AcDbArc")
          (cons 50  0.03491231)
          (cons 51  1.62075305)
         )
         (list
          (cons 0 "LINE")
          (cons 100 "AcDbEntity")
          (cons 67 0)
          (cons 8 "0")
          (cons 62 1)
          (cons 6 "Continuous")
          (cons 100 "AcDbLine")
          (list 10 0.90051598 -0.14081364 0.00000000)
          (list 11 0.90101827 -0.14282910 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.88466544 -0.15258011 0.00000000)
          (list 11 0.88173334 -0.15392319 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90021294 -0.15306147 0.00000000)
          (list 11 0.88236088 -0.15395405 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.90026612 -0.15458470 0.00000000)
          (list 11 0.88272633 -0.15546169 0.00000000)
          (list 210 0.00000000 0.00000000 1.00000000)
         )
         (list (cons 0 "ENDBLK"))
        )
       )
       ((= (strcase BLKNAME) "TRAINSECTION")
        (list
         (list
          (cons 0 "BLOCK")
          (cons 2 "TRAINSECTION")
          (cons 70  0)
          (cons 4 "")
          (list 10 0.00000000 0.00000000 0.00000000)
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.24400000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.24400000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.98500000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.98500000 0.37264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.19260839 0.37264481 0.00000000)
          (cons 40  0.00000000)
          (cons 41  0.00000000)
          (cons 42  0.36674153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.38990017 0.53984304 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.53397065 1.40637923 0.00000000)
          (cons 40  0.00000000)
          (cons 41  0.00000000)
          (cons 42  0.03126153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.55309759 1.59278654 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.59200204 2.57105401 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.59200204 2.73424074 0.00000000)
          (cons 40  0.00000000)
          (cons 41  0.00000000)
          (cons 42  0.22029118)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.53903384 2.84862968 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.28083281 3.06765181 0.00000000)
          (cons 40  0.00000000)
          (cons 41  0.00000000)
          (cons 42  0.17771548)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.12000000 3.49366052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.49366052 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
         )
         (list
          (cons 0 "LINE")
          (cons 100 "AcDbEntity")
          (cons 67 0)
          (cons 8 "0")
          (cons 62 1)
          (cons 6 "CENTER")
          (cons 100 "AcDbLine")
          (list 10 -1.04663306 0.00000000 0.00000000)
          (list 11 1.00417210 0.00000000 0.00000000)
          (list 210 0.00000000 0.00000000 1.00000000)
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.70500000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.70500000 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.13419281 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.19640989 0.63050138 0.00000000)
          (cons 40  0.00000000)
          (cons 41  0.00000000)
          (cons 42  0.23680896)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.20043142 0.63407757 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.25847950 0.78241446 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.26469703 0.84193015 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.31417907 1.31558441 0.00000000)
          (cons 40  0.00000000)
          (cons 41  0.00000000)
          (cons 42  0.04350349)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.32014277 1.66351168 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.24431542 2.74789338 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.28681165 2.75086501 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.27966113 2.85312219 0.00000000)
          (cons 40  0.00000000)
          (cons 41  0.00000000)
          (cons 42  0.22584867)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.21626311 2.96539115 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 1.10681069 3.04229668 0.00000000)
          (cons 40  0.00000000)
          (cons 41  0.00000000)
          (cons 42  0.15433180)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.39226450 0.00000000)
          (cons 40  0.00000000)
          (cons 41  0.00000000)
          (cons 42  0.15433180)
          (cons 91 0)
          (cons 70 0)
          (cons 50  0.00000000)
         )
         (list
          (cons 0 "SEQEND")
          (cons 100 "AcDbEntity")
          (cons 67 0)
          (cons 8 "0")
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.24400000 0.02266052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.24400000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.98500000 0.34264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.98500000 0.37264481 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.19260839 0.37264481 0.00000000)
          (cons 40  0.00000000)
          (cons 41  0.00000000)
          (cons 42  -0.36674153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.38990017 0.53984304 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.53397065 1.40637923 0.00000000)
          (cons 40  0.00000000)
          (cons 41  0.00000000)
          (cons 42  -0.03126153)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.55309759 1.59278654 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.59200204 2.57105401 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.59200204 2.73424074 0.00000000)
          (cons 40  0.00000000)
          (cons 41  0.00000000)
          (cons 42  -0.22029118)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.53903384 2.84862968 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.28083281 3.06765181 0.00000000)
          (cons 40  0.00000000)
          (cons 41  0.00000000)
          (cons 42  -0.17771548)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.12000000 3.49366052 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.49366052 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
         )
         (list
          (cons 0 "POLYLINE")
          (cons 100 "AcDbEntity")
          (cons 67 0)
          (cons 8 "0")
          (cons 100 "AcDb2dPolyline")
          (cons 66 1)
          (list 10 0.00000000 0.00000000 0.00000000)
          (cons 70 0)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 100 "AcDbVertex")
          (cons 100 "AcDb2dVertex")
          (list 10 0.00000000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.70500000 0.19226609 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -0.70500000 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.13419281 0.61383041 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.19640989 0.63050138 0.00000000)
          (cons 40  0.00000000)
          (cons 41  0.00000000)
          (cons 42  -0.23680896)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.20043142 0.63407757 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.25847950 0.78241446 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.26469703 0.84193015 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.31417907 1.31558441 0.00000000)
          (cons 40  0.00000000)
          (cons 41  0.00000000)
          (cons 42  -0.04350349)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.32014277 1.66351168 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.24431542 2.74789338 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.28681165 2.75086501 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.27966113 2.85312219 0.00000000)
          (cons 40  0.00000000)
          (cons 41  0.00000000)
          (cons 42  -0.22584867)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.21626311 2.96539115 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 -1.10681069 3.04229668 0.00000000)
          (cons 40  0.00000000)
          (cons 41  0.00000000)
          (cons 42  -0.15433180)
          (cons 91 0)
          (cons 70 0)
          (cons 50  0.00000000)
         )
         (list
          (cons 0 "VERTEX")
          (cons 100 "AcDbEntity")
          (cons 67 0)
          (cons 8 "0")
          (cons 100 "AcDbVertex")
          (cons 100 "AcDb2dVertex")
          (list 10 0.00000000 3.39226450 0.00000000)
          (cons 40  0.00000000)
          (cons 41  0.00000000)
          (cons 42  -0.15433180)
          (cons 91 0)
          (cons 70 0)
          (cons 50  0.00000000)
         )
         (list
          (cons 0 "SEQEND")
          (cons 100 "AcDbEntity")
          (cons 67 0)
          (cons 8 "0")
         )
         (list
          (cons 0 "LINE")
          (cons 100 "AcDbEntity")
          (cons 67 0)
          (cons 8 "0")
          (cons 62 1)
          (cons 6 "CENTER")
          (cons 100 "AcDbLine")
          (list 10 0.00000000 -0.48642537 0.00000000)
          (list 11 0.00000000 4.05187199 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.91229985 -0.33897276 0.00000000)
          (list 11 -0.91229985 -0.35078869 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90267615 -0.35078869 0.00000000)
          (list 11 -0.90267615 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88342874 -0.35078869 0.00000000)
          (list 11 -0.88342874 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.60710504 -0.33897276 0.00000000)
          (list 11 -0.60710504 -0.35078869 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.63597615 -0.35078869 0.00000000)
          (list 11 -0.63597615 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.61672874 -0.35078869 0.00000000)
          (list 11 -0.61672874 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.64559985 -0.35078869 0.00000000)
          (list 11 -0.64559985 -0.33897276 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.87380504 -0.35078869 0.00000000)
          (list 11 -0.87380504 -0.33897276 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.87861689 -0.34491297 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 -0.90748800 -0.34491297 0.00000000)
          (cons 40  0.00759460)
          (list 210 0.00000000 0.00000000 1.00000000)
          (cons 100 "AcDbArc")
          (cons 50  4.02620608)
          (cons 51  5.39857188)
         )
         (list
          (cons 0 "LINE")
          (cons 100 "AcDbEntity")
          (cons 67 0)
          (cons 8 "0")
          (cons 62 1)
          (cons 6 "Continuous")
          (cons 100 "AcDbLine")
          (list 10 -0.87861689 -0.35250778 0.00000000)
          (list 11 -0.90748800 -0.35250778 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89305244 -0.32470996 0.00000000)
          (cons 40  0.02779776)
          (list 210 0.00000000 0.00000000 1.00000000)
          (cons 100 "AcDbArc")
          (cons 50  4.35886680)
          (cons 51  5.06591116)
         )
         (list
          (cons 0 "ARC")
          (cons 100 "AcDbEntity")
          (cons 67 0)
          (cons 8 "0")
          (cons 62 1)
          (cons 100 "AcDbCircle")
          (list 10 -0.62635244 -0.32470996 0.00000000)
          (cons 40  0.02779776)
          (list 210 0.00000000 0.00000000 1.00000000)
          (cons 100 "AcDbArc")
          (cons 50  4.35886680)
          (cons 51  5.06591116)
         )
         (list
          (cons 0 "LINE")
          (cons 100 "AcDbEntity")
          (cons 67 0)
          (cons 8 "0")
          (cons 62 1)
          (cons 6 "Continuous")
          (cons 100 "AcDbLine")
          (list 10 -0.64078800 -0.35250778 0.00000000)
          (list 11 -0.61191689 -0.35250778 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.64078800 -0.34491297 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 -0.61191689 -0.34491297 0.00000000)
          (cons 40  0.00759460)
          (list 210 0.00000000 0.00000000 1.00000000)
          (cons 100 "AcDbArc")
          (cons 50  4.02620608)
          (cons 51  5.39857188)
         )
         (list
          (cons 0 "LINE")
          (cons 100 "AcDbEntity")
          (cons 67 0)
          (cons 8 "0")
          (cons 62 1)
          (cons 6 "Continuous")
          (cons 100 "AcDbLine")
          (list 10 -0.69431261 -0.21482876 0.00000000)
          (list 11 -0.75970244 -0.21482876 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.80667000 -0.18806435 0.00000000)
          (list 11 -0.71273486 -0.18806435 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.80871883 -0.18501635 0.00000000)
          (list 11 -0.71068606 -0.18501635 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.82923307 -0.16502980 0.00000000)
          (list 11 -0.69031645 -0.17197566 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.75970244 -0.21673376 0.00000000)
          (list 11 -0.56723394 -0.21673376 0.00000000)
          (list 210 0.00000000 0.00000000 1.00000000)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 -0.87555244 -0.21992629 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.54951744 -0.21992629 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 -0.76845357 -0.12956735 0.00000000)
          (cons 40  0.00000000)
          (cons 41  0.00000000)
          (cons 42  0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.76335470 -0.05359212 0.00000000)
          (cons 40  0.00000000)
          (cons 41  0.00000000)
          (cons 42  0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.77685274 -0.03613117 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78626869 -0.03327115 0.00000000)
          (cons 40  0.00000000)
          (cons 41  0.00000000)
          (cons 42  -0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78739919 -0.03162037 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78582129 -0.01061412 0.00000000)
          (cons 40  0.00000000)
          (cons 41  0.00000000)
          (cons 42  -0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.77953528 -0.00236373 0.00000000)
          (cons 40  0.00000000)
          (cons 41  0.00000000)
          (cons 42  -0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.76717895 -0.00013950 0.00000000)
          (cons 40  0.00000000)
          (cons 41  0.00000000)
          (cons 42  -0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.75129895 -0.00043630 0.00000000)
          (cons 40  0.00000000)
          (cons 41  0.00000000)
          (cons 42  -0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.73546856 -0.00172502 0.00000000)
          (cons 40  0.00000000)
          (cons 41  0.00000000)
          (cons 42  -0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.72339572 -0.00517070 0.00000000)
          (cons 40  0.00000000)
          (cons 41  0.00000000)
          (cons 42  -0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.71796404 -0.01400698 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.71848940 -0.03506586 0.00000000)
          (cons 40  0.00000000)
          (cons 41  0.00000000)
          (cons 42  -0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.71977892 -0.03659564 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.72943321 -0.03850215 0.00000000)
          (cons 40  0.00000000)
          (cons 41  0.00000000)
          (cons 42  0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.74460567 -0.05452957 0.00000000)
          (cons 40  0.00000000)
          (cons 41  0.00000000)
          (cons 42  0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.74711080 -0.13063449 0.00000000)
          (cons 40  0.00000000)
          (cons 41  0.00000000)
          (cons 42  0.30975875)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.73364997 -0.14744680 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.69057987 -0.16052900 0.00000000)
          (cons 40  0.00000000)
          (cons 41  0.00000000)
          (cons 42  -0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.68944687 -0.16213983 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.68985971 -0.17039648 0.00000000)
          (cons 40  0.00000000)
          (cons 41  0.00000000)
          (cons 42  -0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.69153761 -0.17191458 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.75970246 -0.16850634 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82786731 -0.16509810 0.00000000)
          (cons 40  0.00000000)
          (cons 41  0.00000000)
          (cons 42  -0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82938541 -0.16342019 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82897258 -0.15516355 0.00000000)
          (cons 40  0.00000000)
          (cons 41  0.00000000)
          (cons 42  -0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.82768455 -0.15367376 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.78352430 -0.14495308 0.00000000)
          (cons 40  0.00000000)
          (cons 41  0.00000000)
          (cons 42  0.30975875)
          (cons 91 0)
          (cons 70 0)
          (cons 50  0.00000000)
         )
         (list
          (cons 0 "SEQEND")
          (cons 100 "AcDbEntity")
          (cons 67 0)
          (cons 8 "0")
          (cons 62 1)
         )
         (list
          (cons 0 "ARC")
          (cons 100 "AcDbEntity")
          (cons 67 0)
          (cons 8 "0")
          (cons 62 1)
          (cons 6 "Continuous")
          (cons 100 "AcDbCircle")
          (list 10 -0.88224768 -0.16174327 0.00000000)
          (cons 40  0.00635001)
          (list 210 0.00000000 0.00000000 1.00000000)
          (cons 100 "AcDbArc")
          (cons 50  4.66243086)
          (cons 51  5.75958867)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.92306764 -0.33173376 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.92306764 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.86303724 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.86303724 -0.33173376 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "LINE")
          (cons 100 "AcDbEntity")
          (cons 67 0)
          (cons 8 "0")
          (cons 62 1)
          (cons 6 "Continuous")
          (cons 100 "AcDbLine")
          (list 10 -0.84091894 -0.21038376 0.00000000)
          (list 11 -0.95109144 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.85330144 -0.20809776 0.00000000)
          (list 11 -0.95217094 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.95217094 -0.21673376 0.00000000)
          (list 11 -0.75970244 -0.21673376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85787146 -0.15838433 0.00000000)
          (cons 40  0.02540000)
          (list 210 0.00000000 0.00000000 1.00000000)
          (cons 100 "AcDbArc")
          (cons 50  0.18065653)
          (cons 51  2.87664897)
         )
         (list
          (cons 0 "LINE")
          (cons 100 "AcDbEntity")
          (cons 67 0)
          (cons 8 "0")
          (cons 62 1)
          (cons 6 "Continuous")
          (cons 100 "AcDbLine")
          (list 10 -0.91306764 -0.20085876 0.00000000)
          (list 11 -0.87303724 -0.20085876 0.00000000)
          (list 210 0.00000000 0.00000000 1.00000000)
         )
         (list
          (cons 0 "LINE")
          (cons 100 "AcDbEntity")
          (cons 67 0)
          (cons 8 "0")
          (cons 62 1)
          (cons 100 "AcDbLine")
          (list 10 -0.87825461 -0.13505188 0.00000000)
          (list 11 -0.87255840 -0.13766107 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.86919991 -0.15184384 0.00000000)
          (list 11 -0.87674841 -0.16491827 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.87861689 -0.19491855 0.00000000)
          (cons 40  0.00759460)
          (list 210 0.00000000 0.00000000 1.00000000)
          (cons 100 "AcDbArc")
          (cons 50  0.88461343)
          (cons 51  2.25697923)
         )
         (list
          (cons 0 "LINE")
          (cons 100 "AcDbEntity")
          (cons 67 0)
          (cons 8 "0")
          (cons 62 1)
          (cons 6 "Continuous")
          (cons 100 "AcDbLine")
          (list 10 -0.91306764 -0.20809776 0.00000000)
          (list 11 -0.87303724 -0.20809776 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85755097 -0.15373334 0.00000000)
          (cons 40  0.02788666)
          (list 210 0.00000000 0.00000000 1.00000000)
          (cons 100 "AcDbArc")
          (cons 50  1.24743899)
          (cons 51  2.47348806)
         )
         (list
          (cons 0 "ARC")
          (cons 100 "AcDbEntity")
          (cons 67 0)
          (cons 8 "0")
          (cons 62 1)
          (cons 100 "AcDbCircle")
          (list 10 -0.85755101 -0.15373332 0.00000000)
          (cons 40  0.04795266)
          (list 210 0.00000000 0.00000000 1.00000000)
          (cons 100 "AcDbArc")
          (cons 50  1.45175629)
          (cons 51  2.87134456)
         )
         (list
          (cons 0 "ARC")
          (cons 100 "AcDbEntity")
          (cons 67 0)
          (cons 8 "0")
          (cons 62 1)
          (cons 6 "Continuous")
          (cons 100 "AcDbCircle")
          (list 10 -0.90857715 -0.16441111 0.00000000)
          (cons 40  0.00317500)
          (list 210 0.00000000 0.00000000 1.00000000)
          (cons 100 "AcDbArc")
          (cons 50  5.14873404)
          (cons 51  6.24828281)
         )
         (list
          (cons 0 "LINE")
          (cons 100 "AcDbEntity")
          (cons 67 0)
          (cons 8 "0")
          (cons 62 1)
          (cons 6 "Continuous")
          (cons 100 "AcDbLine")
          (list 10 -0.90505918 -0.15464920 0.00000000)
          (list 11 -0.90616280 -0.18625376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89620743 -0.17045610 0.00000000)
          (cons 40  0.00304800)
          (list 210 0.00000000 0.00000000 1.00000000)
          (cons 100 "AcDbArc")
          (cons 50  1.52084581)
          (cons 51  3.10633488)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 -0.96988744 -0.21992629 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 -0.91055244 -0.21992629 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "LINE")
          (cons 100 "AcDbEntity")
          (cons 67 0)
          (cons 8 "0")
          (cons 62 1)
          (cons 6 "Continuous")
          (cons 100 "AcDbLine")
          (list 10 -0.94055951 -0.18282803 0.00000000)
          (list 11 -0.90723517 -0.16728862 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.94461444 -0.18625376 0.00000000)
          (list 11 -0.90416494 -0.18625376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.95096444 -0.20174776 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.95109144 -0.21673376 0.00000000)
          (list 11 -0.95109144 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.95193892 -0.21673376 0.00000000)
          (list 11 -0.95109144 -0.21588629 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.95217094 -0.21673376 0.00000000)
          (list 11 -0.95217094 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.94143944 -0.18420924 0.00000000)
          (list 11 -0.94143944 -0.18625376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.94461444 -0.20174776 0.00000000)
          (list 11 -0.94461444 -0.18625376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.93991545 -0.18420925 0.00000000)
          (cons 40  0.00152400)
          (list 210 0.00000000 0.00000000 1.00000000)
          (cons 100 "AcDbArc")
          (cons 50  2.00712794)
          (cons 51  3.14158597)
         )
         (list
          (cons 0 "LINE")
          (cons 100 "AcDbEntity")
          (cons 67 0)
          (cons 8 "0")
          (cons 62 1)
          (cons 6 "Continuous")
          (cons 100 "AcDbLine")
          (list 10 -0.90416494 -0.21673376 0.00000000)
          (list 11 -0.90416494 -0.33173376 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.90340294 -0.33173376 0.00000000)
          (list 11 -0.90340294 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88193994 -0.21673376 0.00000000)
          (list 11 -0.88193994 -0.33173376 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.88270194 -0.33173376 0.00000000)
          (list 11 -0.88270194 -0.21673376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.90748800 -0.19491855 0.00000000)
          (cons 40  0.00759460)
          (list 210 0.00000000 0.00000000 1.00000000)
          (cons 100 "AcDbArc")
          (cons 50  0.88461343)
          (cons 51  2.25697923)
         )
         (list
          (cons 0 "LINE")
          (cons 100 "AcDbEntity")
          (cons 67 0)
          (cons 8 "0")
          (cons 62 1)
          (cons 6 "Continuous")
          (cons 100 "AcDbLine")
          (list 10 -0.91229985 -0.20085876 0.00000000)
          (list 11 -0.91229985 -0.18904283 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.92096974 -0.21038376 0.00000000)
          (list 11 -0.92096974 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.92797744 -0.21038376 0.00000000)
          (list 11 -0.92797744 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.91306764 -0.20085876 0.00000000)
          (list 11 -0.91306764 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.93280344 -0.20809776 0.00000000)
          (list 11 -0.93280344 -0.21038376 0.00000000)
          (list 210 0.00000000 0.00000000 1.00000000)
         )
         (list
          (cons 0 "LINE")
          (cons 100 "AcDbEntity")
          (cons 67 0)
          (cons 8 "0")
          (cons 62 1)
          (cons 100 "AcDbLine")
          (list 10 -0.90416494 -0.17042964 0.00000000)
          (list 11 -0.88193994 -0.17042964 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89305244 -0.21512155 0.00000000)
          (cons 40  0.02779776)
          (list 210 0.00000000 0.00000000 1.00000000)
          (cons 100 "AcDbArc")
          (cons 50  1.21727415)
          (cons 51  1.92431851)
         )
         (list
          (cons 0 "LINE")
          (cons 100 "AcDbEntity")
          (cons 67 0)
          (cons 8 "0")
          (cons 62 1)
          (cons 6 "Continuous")
          (cons 100 "AcDbLine")
          (list 10 -0.87861689 -0.18732373 0.00000000)
          (list 11 -0.90748800 -0.18732373 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90267615 -0.18904283 0.00000000)
          (list 11 -0.90267615 -0.20085876 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.90340294 -0.18732373 0.00000000)
          (list 11 -0.90340294 -0.17042964 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90416494 -0.17042964 0.00000000)
          (list 11 -0.90416494 -0.18732373 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89925352 -0.17034866 0.00000000)
          (list 11 -0.89925635 -0.17042964 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89605518 -0.16741082 0.00000000)
          (list 11 -0.88256478 -0.16808534 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88342874 -0.18904283 0.00000000)
          (list 11 -0.88342874 -0.20085876 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.88270194 -0.18732373 0.00000000)
          (list 11 -0.88270194 -0.17042964 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.88193994 -0.17042964 0.00000000)
          (list 11 -0.88193994 -0.18732373 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89559430 -0.20809776 0.00000000)
          (list 11 -0.88835530 -0.20085876 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.89774959 -0.20809776 0.00000000)
          (list 11 -0.89051059 -0.20085876 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.90351318 -0.15470353 0.00000000)
          (list 11 -0.88597339 -0.15558051 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.90345999 -0.15318029 0.00000000)
          (list 11 -0.88560793 -0.15407287 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.89447511 -0.14511019 0.00000000)
          (cons 40  0.01003300)
          (list 210 0.00000000 0.00000000 1.00000000)
          (cons 100 "AcDbArc")
          (cons 50  2.92404561)
          (cons 51  4.10397118)
         )
         (list
          (cons 0 "LINE")
          (cons 100 "AcDbEntity")
          (cons 67 0)
          (cons 8 "0")
          (cons 62 1)
          (cons 6 "Continuous")
          (cons 100 "AcDbLine")
          (list 10 -0.90376304 -0.14093246 0.00000000)
          (list 11 -0.90426533 -0.14294793 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.90353610 -0.15470244 0.00000000)
          (cons 40  0.00152400)
          (list 210 0.00000000 0.00000000 1.00000000)
          (cons 100 "AcDbArc")
          (cons 50  1.52083960)
          (cons 51  3.10668034)
         )
         (list
          (cons 0 "ARC")
          (cons 100 "AcDbEntity")
          (cons 67 0)
          (cons 8 "0")
          (cons 62 1)
          (cons 6 "Continuous")
          (cons 100 "AcDbCircle")
          (list 10 -0.90358963 -0.15622561 0.00000000)
          (cons 40  0.00152400)
          (list 210 0.00000000 0.00000000 1.00000000)
          (cons 100 "AcDbArc")
          (cons 50  1.52081044)
          (cons 51  3.10669071)
         )
         (list
          (cons 0 "ARC")
          (cons 100 "AcDbEntity")
          (cons 67 0)
          (cons 8 "0")
          (cons 62 1)
          (cons 100 "AcDbCircle")
          (list 10 -0.89447511 -0.14511019 0.00000000)
          (cons 40  0.01003300)
          (list 210 0.00000000 0.00000000 1.00000000)
          (cons 100 "AcDbArc")
          (cons 50  5.22089241)
          (cons 51  6.03683623)
         )
         (list
          (cons 0 "LINE")
          (cons 100 "AcDbEntity")
          (cons 67 0)
          (cons 8 "0")
          (cons 62 1)
          (cons 100 "AcDbLine")
          (list 10 -0.88791250 -0.15269894 0.00000000)
          (list 11 -0.88498040 -0.15404201 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.88581494 -0.15240948 0.00000000)
          (cons 40  0.00317500)
          (list 210 0.00000000 0.00000000 1.00000000)
          (cons 100 "AcDbArc")
          (cons 50  4.66241596)
          (cons 51  6.07254591)
         )
         (list
          (cons 0 "ARC")
          (cons 100 "AcDbEntity")
          (cons 67 0)
          (cons 8 "0")
          (cons 62 1)
          (cons 6 "Continuous")
          (cons 100 "AcDbCircle")
          (list 10 -0.88544940 -0.15090185 0.00000000)
          (cons 40  0.00317500)
          (list 210 0.00000000 0.00000000 1.00000000)
          (cons 100 "AcDbArc")
          (cons 50  4.66243394)
          (cons 51  6.01824134)
         )
         (list
          (cons 0 "ARC")
          (cons 100 "AcDbEntity")
          (cons 67 0)
          (cons 8 "0")
          (cons 62 1)
          (cons 100 "AcDbCircle")
          (list 10 -0.85755089 -0.15373311 0.00000000)
          (cons 40  0.02788666)
          (list 210 0.00000000 0.00000000 1.00000000)
          (cons 100 "AcDbArc")
          (cons 50  2.47348747)
          (cons 51  2.91826494)
         )
         (list
          (cons 0 "LINE")
          (cons 100 "AcDbEntity")
          (cons 67 0)
          (cons 8 "0")
          (cons 62 1)
          (cons 6 "Continuous")
          (cons 100 "AcDbLine")
          (list 10 -0.84654296 -0.16492484 0.00000000)
          (list 11 -0.85777616 -0.18438135 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84707844 -0.20174776 0.00000000)
          (list 11 -0.84707844 -0.16585233 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84335823 -0.15881190 0.00000000)
          (list 11 -0.84452867 -0.19232916 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.81461567 -0.21092434 0.00000000)
          (cons 40  0.00152400)
          (list 210 0.00000000 0.00000000 1.00000000)
          (cons 100 "AcDbArc")
          (cons 50  4.71238705)
          (cons 51  6.23082632)
         )
         (list
          (cons 0 "LINE")
          (cons 100 "AcDbEntity")
          (cons 67 0)
          (cons 8 "0")
          (cons 62 1)
          (cons 6 "Continuous")
          (cons 100 "AcDbLine")
          (list 10 -0.82509322 -0.21482876 0.00000000)
          (list 11 -0.75970244 -0.21482876 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.86327543 -0.18120634 0.00000000)
          (cons 40  0.00635001)
          (list 210 0.00000000 0.00000000 1.00000000)
          (cons 100 "AcDbArc")
          (cons 50  4.71238703)
          (cons 51  5.75958588)
         )
         (list
          (cons 0 "LINE")
          (cons 100 "AcDbEntity")
          (cons 67 0)
          (cons 8 "0")
          (cons 62 1)
          (cons 6 "Continuous")
          (cons 100 "AcDbLine")
          (list 10 -0.87380504 -0.18904283 0.00000000)
          (list 11 -0.87380504 -0.20085876 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.87380504 -0.18755635 0.00000000)
          (list 11 -0.86327544 -0.18755635 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.85812744 -0.21038376 0.00000000)
          (list 11 -0.85812744 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.86513515 -0.21038376 0.00000000)
          (list 11 -0.86513515 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.87303724 -0.20085876 0.00000000)
          (list 11 -0.87303724 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.85330144 -0.20809649 0.00000000)
          (list 11 -0.85330144 -0.21038376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85342844 -0.20174776 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.84300559 -0.19390635 0.00000000)
          (list 11 -0.83113834 -0.19390635 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.84300559 -0.19238235 0.00000000)
          (cons 40  0.00152400)
          (list 210 0.00000000 0.00000000 1.00000000)
          (cons 100 "AcDbArc")
          (cons 50  3.10668656)
          (cons 51  4.71238898)
         )
         (list
          (cons 0 "ARC")
          (cons 100 "AcDbEntity")
          (cons 67 0)
          (cons 8 "0")
          (cons 62 1)
          (cons 6 "Continuous")
          (cons 100 "AcDbCircle")
          (list 10 -0.83113834 -0.20178054 0.00000000)
          (cons 40  0.00787400)
          (list 210 0.00000000 0.00000000 1.00000000)
          (cons 100 "AcDbArc")
          (cons 50  0.05236240)
          (cons 51  1.57079607)
         )
         (list
          (cons 0 "LINE")
          (cons 100 "AcDbEntity")
          (cons 67 0)
          (cons 8 "0")
          (cons 62 1)
          (cons 6 "Continuous")
          (cons 100 "AcDbLine")
          (list 10 -0.83456894 -0.20149376 0.00000000)
          (list 11 -0.83088594 -0.20149376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.83456894 -0.20149376 0.00000000)
          (list 11 -0.83456894 -0.20403376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.82504652 -0.20322575 0.00000000)
          (cons 40  0.00111252)
          (list 210 0.00000000 0.00000000 1.00000000)
          (cons 100 "AcDbArc")
          (cons 50  0.05236168)
          (cons 51  3.10668488)
         )
         (list
          (cons 0 "ARC")
          (cons 100 "AcDbEntity")
          (cons 67 0)
          (cons 8 "0")
          (cons 62 1)
          (cons 6 "Continuous")
          (cons 100 "AcDbCircle")
          (list 10 -0.82124822 -0.21092434 0.00000000)
          (cons 40  0.00152400)
          (list 210 0.00000000 0.00000000 1.00000000)
          (cons 100 "AcDbArc")
          (cons 50  3.19394763)
          (cons 51  4.71238690)
         )
         (list
          (cons 0 "ARC")
          (cons 100 "AcDbEntity")
          (cons 67 0)
          (cons 8 "0")
          (cons 62 1)
          (cons 6 "Continuous")
          (cons 100 "AcDbCircle")
          (list 10 -0.82115506 -0.21254209 0.00000000)
          (cons 40  0.00228600)
          (list 210 0.00000000 0.00000000 1.00000000)
          (cons 100 "AcDbArc")
          (cons 50  3.19393752)
          (cons 51  4.71238789)
         )
         (list
          (cons 0 "ARC")
          (cons 100 "AcDbEntity")
          (cons 67 0)
          (cons 8 "0")
          (cons 62 1)
          (cons 100 "AcDbCircle")
          (list 10 -0.83456894 -0.21038376 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.82821894 -0.20416076 0.00000000)
          (list 11 -0.82821894 -0.21038376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.82509321 -0.21635275 0.00000000)
          (cons 40  0.00152399)
          (list 210 0.00000000 0.00000000 1.00000000)
          (cons 100 "AcDbArc")
          (cons 50  1.57080019)
          (cons 51  3.10668917)
         )
         (list
          (cons 0 "LINE")
          (cons 100 "AcDbEntity")
          (cons 67 0)
          (cons 8 "0")
          (cons 62 1)
          (cons 6 "Continuous")
          (cons 100 "AcDbLine")
          (list 10 -0.82124822 -0.21244835 0.00000000)
          (list 11 -0.81461567 -0.21244835 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.83088594 -0.20416076 0.00000000)
          (cons 40  0.00266700)
          (list 210 0.00000000 0.00000000 1.00000000)
          (cons 100 "AcDbArc")
          (cons 50  0.00000000)
          (cons 51  1.57079633)
         )
         (list
          (cons 0 "ARC")
          (cons 100 "AcDbEntity")
          (cons 67 0)
          (cons 8 "0")
          (cons 62 1)
          (cons 6 "Continuous")
          (cons 100 "AcDbCircle")
          (list 10 -0.84091894 -0.20403376 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 -0.82615836 -0.20318692 0.00000000)
          (list 11 -0.82663144 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.82343790 -0.21266239 0.00000000)
          (list 11 -0.82393553 -0.20316752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.82277014 -0.21100410 0.00000000)
          (list 11 -0.82327511 -0.20136826 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.80667000 -0.19035035 0.00000000)
          (cons 40  0.00228600)
          (list 210 0.00000000 0.00000000 1.00000000)
          (cons 100 "AcDbArc")
          (cons 50  1.57079633)
          (cons 51  3.08923306)
         )
         (list
          (cons 0 "ARC")
          (cons 100 "AcDbEntity")
          (cons 67 0)
          (cons 8 "0")
          (cons 62 1)
          (cons 6 "Continuous")
          (cons 100 "AcDbCircle")
          (list 10 -0.80871884 -0.18819135 0.00000000)
          (cons 40  0.00317500)
          (list 210 0.00000000 0.00000000 1.00000000)
          (cons 100 "AcDbArc")
          (cons 50  1.57079503)
          (cons 51  3.08923156)
         )
         (list
          (cons 0 "ARC")
          (cons 100 "AcDbEntity")
          (cons 67 0)
          (cons 8 "0")
          (cons 62 1)
          (cons 6 "Continuous")
          (cons 100 "AcDbCircle")
          (list 10 -0.81241133 -0.21254275 0.00000000)
          (cons 40  0.00228600)
          (list 210 0.00000000 0.00000000 1.00000000)
          (cons 100 "AcDbArc")
          (cons 50  4.71238705)
          (cons 51  6.23082632)
         )
         (list
          (cons 0 "LINE")
          (cons 100 "AcDbEntity")
          (cons 67 0)
          (cons 8 "0")
          (cons 62 1)
          (cons 6 "Continuous")
          (cons 100 "AcDbLine")
          (list 10 -0.81309375 -0.21100410 0.00000000)
          (list 11 -0.81188949 -0.18802518 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.81012846 -0.21266239 0.00000000)
          (list 11 -0.80895287 -0.19023071 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.85862670 -0.16286834 0.00000000)
          (cons 40  0.05715000)
          (list 210 0.00000000 0.00000000 1.00000000)
          (cons 100 "AcDbArc")
          (cons 50  0.39733728)
          (cons 51  1.45204144)
         )
         (list
          (cons 0 "ARC")
          (cons 100 "AcDbEntity")
          (cons 67 0)
          (cons 8 "0")
          (cons 62 1)
          (cons 6 "Continuous")
          (cons 100 "AcDbCircle")
          (list 10 -0.85787146 -0.15838434 0.00000000)
          (cons 40  0.01308100)
          (list 210 0.00000000 0.00000000 1.00000000)
          (cons 100 "AcDbArc")
          (cons 50  5.75958633)
          (cons 51  2.61799368)
         )
         (list
          (cons 0 "ARC")
          (cons 100 "AcDbEntity")
          (cons 67 0)
          (cons 8 "0")
          (cons 62 1)
          (cons 100 "AcDbCircle")
          (list 10 -0.86047397 -0.16245432 0.00000000)
          (cons 40  0.03708400)
          (list 210 0.00000000 0.00000000 1.00000000)
          (cons 100 "AcDbArc")
          (cons 50  0.48069660)
          (cons 51  1.24742577)
         )
         (list
          (cons 0 "CIRCLE")
          (cons 100 "AcDbEntity")
          (cons 67 0)
          (cons 8 "0")
          (cons 62 1)
          (cons 100 "AcDbCircle")
          (list 10 -0.85805989 -0.15533774 0.00000000)
          (cons 40  0.01003300)
          (list 210 0.00000000 0.00000000 1.00000000)
         )
         (list
          (cons 0 "ARC")
          (cons 100 "AcDbEntity")
          (cons 67 0)
          (cons 8 "0")
          (cons 62 1)
          (cons 100 "AcDbCircle")
          (list 10 -0.85787144 -0.15314603 0.00000000)
          (cons 40  0.01008126)
          (list 210 0.00000000 0.00000000 1.00000000)
          (cons 100 "AcDbArc")
          (cons 50  0.40917332)
          (cons 51  2.73241869)
         )
         (list
          (cons 0 "LINE")
          (cons 100 "AcDbEntity")
          (cons 67 0)
          (cons 8 "0")
          (cons 62 1)
          (cons 100 "AcDbLine")
          (list 10 -0.87350405 -0.15929885 0.00000000)
          (list 11 -0.86223810 -0.16445931 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84483212 -0.15734109 0.00000000)
          (list 11 -0.83245244 -0.15734109 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.84483212 -0.15734109 0.00000000)
          (list 11 -0.83245244 -0.15734109 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.84183517 -0.15886508 0.00000000)
          (cons 40  0.00152399)
          (list 210 0.00000000 0.00000000 1.00000000)
          (cons 100 "AcDbArc")
          (cons 50  1.57080019)
          (cons 51  3.10668917)
         )
         (list
          (cons 0 "LINE")
          (cons 100 "AcDbEntity")
          (cons 67 0)
          (cons 8 "0")
          (cons 62 1)
          (cons 6 "Continuous")
          (cons 100 "AcDbLine")
          (list 10 -0.83072344 -0.16273689 0.00000000)
          (list 11 -0.83611921 -0.15734109 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.82189069 -0.15181245 0.00000000)
          (cons 40  0.01117600)
          (list 210 0.00000000 0.00000000 1.00000000)
          (cons 100 "AcDbArc")
          (cons 50  3.32225661)
          (cons 51  3.73034794)
         )
         (list
          (cons 0 "ARC")
          (cons 100 "AcDbEntity")
          (cons 67 0)
          (cons 8 "0")
          (cons 62 1)
          (cons 100 "AcDbCircle")
          (list 10 -0.83245244 -0.15886509 0.00000000)
          (cons 40  0.00152400)
          (list 210 0.00000000 0.00000000 1.00000000)
          (cons 100 "AcDbArc")
          (cons 50  0.05235839)
          (cons 51  1.57080045)
         )
         (list
          (cons 0 "ARC")
          (cons 100 "AcDbEntity")
          (cons 67 0)
          (cons 8 "0")
          (cons 62 1)
          (cons 6 "Continuous")
          (cons 100 "AcDbCircle")
          (list 10 -0.82915694 -0.16350769 0.00000000)
          (cons 40  0.00152400)
          (list 210 0.00000000 0.00000000 1.00000000)
          (cons 100 "AcDbArc")
          (cons 50  3.19395084)
          (cons 51  4.66241844)
         )
         (list
          (cons 0 "LINE")
          (cons 100 "AcDbEntity")
          (cons 67 0)
          (cons 8 "0")
          (cons 62 1)
          (cons 6 "Continuous")
          (cons 100 "AcDbLine")
          (list 10 -0.83067886 -0.16358746 0.00000000)
          (list 11 -0.83093052 -0.15878533 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.82211799 -0.14583452 0.00000000)
          (cons 40  0.00709647)
          (list 210 0.00000000 0.00000000 1.00000000)
          (cons 100 "AcDbArc")
          (cons 50  2.77219369)
          (cons 51  4.52091742)
         )
         (list
          (cons 0 "ARC")
          (cons 100 "AcDbEntity")
          (cons 67 0)
          (cons 8 "0")
          (cons 62 1)
          (cons 100 "AcDbCircle")
          (list 10 -0.81066054 -0.14355768 0.00000000)
          (cons 40  0.00664210)
          (list 210 0.00000000 0.00000000 1.00000000)
          (cons 100 "AcDbArc")
          (cons 50  5.02355404)
          (cons 51  1.02870600)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.59633724 -0.33173376 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.59633724 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.65636764 -0.33897276 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 -0.65636764 -0.33173376 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "LINE")
          (cons 100 "AcDbEntity")
          (cons 67 0)
          (cons 8 "0")
          (cons 62 1)
          (cons 6 "Continuous")
          (cons 100 "AcDbLine")
          (list 10 -0.63328549 -0.16516317 0.00000000)
          (list 11 -0.61516380 -0.16606922 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.63298516 -0.16670406 0.00000000)
          (list 11 -0.61511043 -0.16759781 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62431267 -0.15378646 0.00000000)
          (cons 40  0.01003300)
          (list 210 0.00000000 0.00000000 1.00000000)
          (cons 100 "AcDbArc")
          (cons 50  6.21237415)
          (cons 51  3.14633739)
         )
         (list
          (cons 0 "LINE")
          (cons 100 "AcDbEntity")
          (cons 67 0)
          (cons 8 "0")
          (cons 62 1)
          (cons 6 "Continuous")
          (cons 100 "AcDbLine")
          (list 10 -0.63641222 -0.17886711 0.00000000)
          (list 11 -0.62244217 -0.17956561 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.66129223 -0.18755635 0.00000000)
          (list 11 -0.62252809 -0.18755635 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.66190186 -0.16351122 0.00000000)
          (cons 40  0.04795206)
          (list 210 0.00000000 0.00000000 1.00000000)
          (cons 100 "AcDbArc")
          (cons 50  0.34986041)
          (cons 51  1.55890984)
         )
         (list
          (cons 0 "LINE")
          (cons 100 "AcDbEntity")
          (cons 67 0)
          (cons 8 "0")
          (cons 62 1)
          (cons 6 "Continuous")
          (cons 100 "AcDbLine")
          (list 10 -0.56831344 -0.21038376 0.00000000)
          (list 11 -0.62584444 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.62876544 -0.19390635 0.00000000)
          (list 11 -0.57945136 -0.19267351 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.63282661 -0.16353302 0.00000000)
          (cons 40  0.00317500)
          (list 210 0.00000000 0.00000000 1.00000000)
          (cons 100 "AcDbArc")
          (cons 50  3.30661926)
          (cons 51  4.66242980)
         )
         (list
          (cons 0 "LINE")
          (cons 100 "AcDbEntity")
          (cons 67 0)
          (cons 8 "0")
          (cons 62 1)
          (cons 6 "Continuous")
          (cons 100 "AcDbLine")
          (list 10 -0.64968491 -0.16168680 0.00000000)
          (list 11 -0.64159438 -0.17570003 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.68871844 -0.17053332 0.00000000)
          (list 11 -0.68847437 -0.16587582 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.66101340 -0.16822728 0.00000000)
          (cons 40  0.01308100)
          (list 210 0.00000000 0.00000000 1.00000000)
          (cons 100 "AcDbArc")
          (cons 50  0.52359898)
          (cons 51  3.66519163)
         )
         (list
          (cons 0 "CIRCLE")
          (cons 100 "AcDbEntity")
          (cons 67 0)
          (cons 8 "0")
          (cons 62 1)
          (cons 100 "AcDbCircle")
          (list 10 -0.66115168 -0.16517839 0.00000000)
          (cons 40  0.01003300)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.68483594 -0.21038376 0.00000000)
          (cons 40  0.00635000)
          (list 210 0.00000000 0.00000000 1.00000000)
          (cons 100 "AcDbArc")
          (cons 50  3.14159265)
          (cons 51  4.71238898)
         )
         (list
          (cons 0 "LINE")
          (cons 100 "AcDbEntity")
          (cons 67 0)
          (cons 8 "0")
          (cons 62 1)
          (cons 6 "Continuous")
          (cons 100 "AcDbLine")
          (list 10 -0.68851894 -0.20149376 0.00000000)
          (list 11 -0.68483594 -0.20149376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.68826657 -0.19390635 0.00000000)
          (list 11 -0.62876544 -0.19390635 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.68851894 -0.20416076 0.00000000)
          (cons 40  0.00266700)
          (list 210 0.00000000 0.00000000 1.00000000)
          (cons 100 "AcDbArc")
          (cons 50  1.57079633)
          (cons 51  3.14159265)
         )
         (list
          (cons 0 "LINE")
          (cons 100 "AcDbEntity")
          (cons 67 0)
          (cons 8 "0")
          (cons 62 1)
          (cons 6 "Continuous")
          (cons 100 "AcDbLine")
          (list 10 -0.69118594 -0.20416076 0.00000000)
          (list 11 -0.69118594 -0.21038376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.69024034 -0.17045348 0.00000000)
          (cons 40  0.00152400)
          (list 210 0.00000000 0.00000000 1.00000000)
          (cons 100 "AcDbArc")
          (cons 50  4.66243298)
          (cons 51  6.23083137)
         )
         (list
          (cons 0 "ARC")
          (cons 100 "AcDbEntity")
          (cons 67 0)
          (cons 8 "0")
          (cons 62 1)
          (cons 100 "AcDbCircle")
          (list 10 -0.69431261 -0.21635276 0.00000000)
          (cons 40  0.00152400)
          (list 210 0.00000000 0.00000000 1.00000000)
          (cons 100 "AcDbArc")
          (cons 50  0.00000000)
          (cons 51  1.57079633)
         )
         (list
          (cons 0 "ARC")
          (cons 100 "AcDbEntity")
          (cons 67 0)
          (cons 8 "0")
          (cons 62 1)
          (cons 6 "Continuous")
          (cons 100 "AcDbCircle")
          (list 10 -0.69435837 -0.20322575 0.00000000)
          (cons 40  0.00111252)
          (list 210 0.00000000 0.00000000 1.00000000)
          (cons 100 "AcDbArc")
          (cons 50  0.03490778)
          (cons 51  3.08923097)
         )
         (list
          (cons 0 "ARC")
          (cons 100 "AcDbEntity")
          (cons 67 0)
          (cons 8 "0")
          (cons 62 1)
          (cons 6 "Continuous")
          (cons 100 "AcDbCircle")
          (list 10 -0.69824985 -0.21254276 0.00000000)
          (cons 40  0.00228600)
          (list 210 0.00000000 0.00000000 1.00000000)
          (cons 100 "AcDbArc")
          (cons 50  4.71238898)
          (cons 51  6.23082363)
         )
         (list
          (cons 0 "LINE")
          (cons 100 "AcDbEntity")
          (cons 67 0)
          (cons 8 "0")
          (cons 62 1)
          (cons 100 "AcDbLine")
          (list 10 -0.69278861 -0.21635276 0.00000000)
          (list 11 -0.69278861 -0.21673376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.69815666 -0.21092435 0.00000000)
          (cons 40  0.00152400)
          (list 210 0.00000000 0.00000000 1.00000000)
          (cons 100 "AcDbArc")
          (cons 50  4.71238898)
          (cons 51  6.23082707)
         )
         (list
          (cons 0 "LINE")
          (cons 100 "AcDbEntity")
          (cons 67 0)
          (cons 8 "0")
          (cons 62 1)
          (cons 6 "Continuous")
          (cons 100 "AcDbLine")
          (list 10 -0.70478923 -0.21244835 0.00000000)
          (list 11 -0.69815666 -0.21244835 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69324653 -0.20318692 0.00000000)
          (list 11 -0.69277344 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69663475 -0.21100410 0.00000000)
          (list 11 -0.69612978 -0.20136827 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69596699 -0.21266240 0.00000000)
          (list 11 -0.69546936 -0.20316752 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.71068606 -0.18819133 0.00000000)
          (cons 40  0.00317500)
          (list 210 0.00000000 0.00000000 1.00000000)
          (cons 100 "AcDbArc")
          (cons 50  0.05235860)
          (cons 51  1.57079513)
         )
         (list
          (cons 0 "ARC")
          (cons 100 "AcDbEntity")
          (cons 67 0)
          (cons 8 "0")
          (cons 62 1)
          (cons 6 "Continuous")
          (cons 100 "AcDbCircle")
          (list 10 -0.71273486 -0.19035035 0.00000000)
          (cons 40  0.00228600)
          (list 210 0.00000000 0.00000000 1.00000000)
          (cons 100 "AcDbArc")
          (cons 50  0.05235847)
          (cons 51  1.57079633)
         )
         (list
          (cons 0 "ARC")
          (cons 100 "AcDbEntity")
          (cons 67 0)
          (cons 8 "0")
          (cons 62 1)
          (cons 100 "AcDbCircle")
          (list 10 -0.70699357 -0.21254276 0.00000000)
          (cons 40  0.00228600)
          (list 210 0.00000000 0.00000000 1.00000000)
          (cons 100 "AcDbArc")
          (cons 50  3.19395112)
          (cons 51  4.71238898)
         )
         (list
          (cons 0 "LINE")
          (cons 100 "AcDbEntity")
          (cons 67 0)
          (cons 8 "0")
          (cons 62 1)
          (cons 6 "Continuous")
          (cons 100 "AcDbLine")
          (list 10 -0.70927643 -0.21266239 0.00000000)
          (list 11 -0.71045200 -0.19023071 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.70631114 -0.21100411 0.00000000)
          (list 11 -0.70751540 -0.18802518 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.70478923 -0.21092435 0.00000000)
          (cons 40  0.00152400)
          (list 210 0.00000000 0.00000000 1.00000000)
          (cons 100 "AcDbArc")
          (cons 50  3.19395212)
          (cons 51  4.71238898)
         )
         (list
          (cons 0 "ARC")
          (cons 100 "AcDbEntity")
          (cons 67 0)
          (cons 8 "0")
          (cons 62 1)
          (cons 6 "Continuous")
          (cons 100 "AcDbCircle")
          (list 10 -0.68826657 -0.20178035 0.00000000)
          (cons 40  0.00787400)
          (list 210 0.00000000 0.00000000 1.00000000)
          (cons 100 "AcDbArc")
          (cons 50  1.57079633)
          (cons 51  3.08923442)
         )
         (list
          (cons 0 "LINE")
          (cons 100 "AcDbEntity")
          (cons 67 0)
          (cons 8 "0")
          (cons 62 1)
          (cons 6 "DASHED")
          (cons 100 "AcDbLine")
          (list 10 -0.63670294 -0.33173376 0.00000000)
          (list 11 -0.63670294 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.63746494 -0.21673376 0.00000000)
          (list 11 -0.63746494 -0.33173376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.64159244 -0.21038376 0.00000000)
          (list 11 -0.67848594 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.67234186 -0.17476780 0.00000000)
          (list 11 -0.66679148 -0.18438135 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.68483594 -0.20149376 0.00000000)
          (list 11 -0.68483594 -0.20403376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.67848594 -0.20403376 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 6 "Continuous")
          (cons 100 "AcDbCircle")
          (list 10 -0.66129222 -0.18120631 0.00000000)
          (cons 40  0.00635000)
          (list 210 0.00000000 0.00000000 1.00000000)
          (cons 100 "AcDbArc")
          (cons 50  3.66519355)
          (cons 51  4.71239040)
         )
         (list
          (cons 0 "ARC")
          (cons 100 "AcDbEntity")
          (cons 67 0)
          (cons 8 "0")
          (cons 62 1)
          (cons 6 "Continuous")
          (cons 100 "AcDbCircle")
          (list 10 -0.63609517 -0.17252491 0.00000000)
          (cons 40  0.00635000)
          (list 210 0.00000000 0.00000000 1.00000000)
          (cons 100 "AcDbArc")
          (cons 50  3.66519004)
          (cons 51  4.66242866)
         )
         (list
          (cons 0 "LINE")
          (cons 100 "AcDbEntity")
          (cons 67 0)
          (cons 8 "0")
          (cons 62 1)
          (cons 6 "Continuous")
          (cons 100 "AcDbLine")
          (list 10 -0.62584444 -0.21038376 0.00000000)
          (list 11 -0.62584444 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.64159244 -0.21038376 0.00000000)
          (list 11 -0.64159244 -0.21673376 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.66014290 -0.17253922 0.00000000)
          (cons 40  0.03708400)
          (list 210 0.00000000 0.00000000 1.00000000)
          (cons 100 "AcDbArc")
          (cons 50  1.76322371)
          (cons 51  2.52595268)
         )
         (list
          (cons 0 "ARC")
          (cons 100 "AcDbEntity")
          (cons 67 0)
          (cons 8 "0")
          (cons 62 1)
          (cons 6 "Continuous")
          (cons 100 "AcDbCircle")
          (list 10 -0.68695245 -0.16595558 0.00000000)
          (cons 40  0.00152400)
          (list 210 0.00000000 0.00000000 1.00000000)
          (cons 100 "AcDbArc")
          (cons 50  2.33720068)
          (cons 51  3.08921738)
         )
         (list
          (cons 0 "ARC")
          (cons 100 "AcDbEntity")
          (cons 67 0)
          (cons 8 "0")
          (cons 62 1)
          (cons 100 "AcDbCircle")
          (list 10 -0.66202828 -0.17270793 0.00000000)
          (cons 40  0.05715000)
          (list 210 0.00000000 0.00000000 1.00000000)
          (cons 100 "AcDbArc")
          (cons 50  1.55860971)
          (cons 51  2.56947374)
         )
         (list
          (cons 0 "ARC")
          (cons 100 "AcDbEntity")
          (cons 67 0)
          (cons 8 "0")
          (cons 62 1)
          (cons 6 "Continuous")
          (cons 100 "AcDbCircle")
          (list 10 -0.70872048 -0.14826766 0.00000000)
          (cons 40  0.00664164)
          (list 210 0.00000000 0.00000000 1.00000000)
          (cons 100 "AcDbArc")
          (cons 50  1.39459995)
          (cons 51  4.16546659)
         )
         (list
          (cons 0 "LINE")
          (cons 100 "AcDbEntity")
          (cons 67 0)
          (cons 8 "0")
          (cons 62 1)
          (cons 6 "Continuous")
          (cons 100 "AcDbLine")
          (list 10 -0.69385434 -0.15761457 0.00000000)
          (list 11 -0.71444930 -0.15162817 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.69316511 -0.14591171 0.00000000)
          (list 11 -0.70755637 -0.14172885 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.69750294 -0.15152840 0.00000000)
          (cons 40  0.00709676)
          (list 210 0.00000000 0.00000000 1.00000000)
          (cons 100 "AcDbArc")
          (cons 50  4.80779445)
          (cons 51  0.91316894)
         )
         (list
          (cons 0 "ARC")
          (cons 100 "AcDbEntity")
          (cons 67 0)
          (cons 8 "0")
          (cons 62 1)
          (cons 100 "AcDbCircle")
          (list 10 -0.66101339 -0.16822729 0.00000000)
          (cons 40  0.02540001)
          (list 210 0.00000000 0.00000000 1.00000000)
          (cons 100 "AcDbArc")
          (cons 50  0.16502661)
          (cons 51  2.82403160)
         )
         (list
          (cons 0 "ARC")
          (cons 100 "AcDbEntity")
          (cons 67 0)
          (cons 8 "0")
          (cons 62 1)
          (cons 6 "Continuous")
          (cons 100 "AcDbCircle")
          (list 10 -0.66190181 -0.16351112 0.00000000)
          (cons 40  0.02788609)
          (list 210 0.00000000 0.00000000 1.00000000)
          (cons 100 "AcDbArc")
          (cons 50  0.19774392)
          (cons 51  1.76322577)
         )
         (list
          (cons 0 "ARC")
          (cons 100 "AcDbEntity")
          (cons 67 0)
          (cons 8 "0")
          (cons 62 1)
          (cons 6 "Continuous")
          (cons 100 "AcDbCircle")
          (list 10 -0.69576061 -0.15680646 0.00000000)
          (cons 40  0.01117600)
          (list 210 0.00000000 0.00000000 1.00000000)
          (cons 100 "AcDbArc")
          (cons 50  5.47880514)
          (cons 51  5.96562864)
         )
         (list
          (cons 0 "LINE")
          (cons 100 "AcDbEntity")
          (cons 67 0)
          (cons 8 "0")
          (cons 62 1)
          (cons 6 "Continuous")
          (cons 100 "AcDbLine")
          (list 10 -0.63434133 -0.15349154 0.00000000)
          (list 11 -0.63440982 -0.15904690 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62457147 -0.15708018 0.00000000)
          (cons 40  0.01003300)
          (list 210 0.00000000 0.00000000 1.00000000)
          (cons 100 "AcDbArc")
          (cons 50  3.23667276)
          (cons 51  4.10386339)
         )
         (list
          (cons 0 "ARC")
          (cons 100 "AcDbEntity")
          (cons 67 0)
          (cons 8 "0")
          (cons 62 1)
          (cons 100 "AcDbCircle")
          (list 10 -0.63312695 -0.16199213 0.00000000)
          (cons 40  0.00317500)
          (list 210 0.00000000 0.00000000 1.00000000)
          (cons 100 "AcDbArc")
          (cons 50  3.36156540)
          (cons 51  4.66243282)
         )
         (list
          (cons 0 "ARC")
          (cons 100 "AcDbEntity")
          (cons 67 0)
          (cons 8 "0")
          (cons 62 1)
          (cons 6 "Continuous")
          (cons 100 "AcDbCircle")
          (list 10 -0.61523991 -0.16759131 0.00000000)
          (cons 40  0.00152400)
          (list 210 0.00000000 0.00000000 1.00000000)
          (cons 100 "AcDbArc")
          (cons 50  0.03489860)
          (cons 51  1.52084017)
         )
         (list
          (cons 0 "LINE")
          (cons 100 "AcDbEntity")
          (cons 67 0)
          (cons 8 "0")
          (cons 62 1)
          (cons 6 "Continuous")
          (cons 100 "AcDbLine")
          (list 10 -0.61523994 -0.21673376 0.00000000)
          (list 11 -0.61523994 -0.33173376 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 -0.61600194 -0.33173376 0.00000000)
          (list 11 -0.61600194 -0.21673376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.60825480 -0.18704159 0.00000000)
          (list 11 -0.57952754 -0.18632340 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.60840298 -0.18625376 0.00000000)
          (list 11 -0.57479044 -0.18625376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.57904388 -0.18290860 0.00000000)
          (list 11 -0.61138275 -0.17302160 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.61518654 -0.16911991 0.00000000)
          (cons 40  0.00152400)
          (list 210 0.00000000 0.00000000 1.00000000)
          (cons 100 "AcDbArc")
          (cons 50  0.03489860)
          (cons 51  1.52083715)
         )
         (list
          (cons 0 "ARC")
          (cons 100 "AcDbEntity")
          (cons 67 0)
          (cons 8 "0")
          (cons 62 1)
          (cons 6 "Continuous")
          (cons 100 "AcDbCircle")
          (list 10 -0.61045447 -0.16998532 0.00000000)
          (cons 40  0.00317500)
          (list 210 0.00000000 0.00000000 1.00000000)
          (cons 100 "AcDbArc")
          (cons 50  3.17648866)
          (cons 51  4.41568060)
         )
         (list
          (cons 0 "ARC")
          (cons 100 "AcDbEntity")
          (cons 67 0)
          (cons 8 "0")
          (cons 62 1)
          (cons 6 "Continuous")
          (cons 100 "AcDbCircle")
          (list 10 -0.62259437 -0.18260976 0.00000000)
          (cons 40  0.00304800)
          (list 210 0.00000000 0.00000000 1.00000000)
          (cons 100 "AcDbArc")
          (cons 50  0.03489992)
          (cons 51  1.52083597)
         )
         (list
          (cons 0 "LINE")
          (cons 100 "AcDbEntity")
          (cons 67 0)
          (cons 8 "0")
          (cons 62 1)
          (cons 6 "Continuous")
          (cons 100 "AcDbLine")
          (list 10 -0.61954824 -0.18250345 0.00000000)
          (list 11 -0.61948195 -0.18440200 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62252809 -0.18450830 0.00000000)
          (cons 40  0.00304800)
          (list 210 0.00000000 0.00000000 1.00000000)
          (cons 100 "AcDbArc")
          (cons 50  4.71238932)
          (cons 51  0.03488134)
         )
         (list
          (cons 0 "LINE")
          (cons 100 "AcDbEntity")
          (cons 67 0)
          (cons 8 "0")
          (cons 62 1)
          (cons 6 "Continuous")
          (cons 100 "AcDbLine")
          (list 10 -0.61319847 -0.18238548 0.00000000)
          (list 11 -0.61371683 -0.16753814 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.60837541 -0.18221710 0.00000000)
          (cons 40  0.00482600)
          (list 210 0.00000000 0.00000000 1.00000000)
          (cons 100 "AcDbArc")
          (cons 50  3.17649126)
          (cons 51  4.73738391)
         )
         (list
          (cons 0 "ARC")
          (cons 100 "AcDbEntity")
          (cons 67 0)
          (cons 8 "0")
          (cons 62 1)
          (cons 100 "AcDbCircle")
          (list 10 -0.60840297 -0.18142776 0.00000000)
          (cons 40  0.00482600)
          (list 210 0.00000000 0.00000000 1.00000000)
          (cons 100 "AcDbArc")
          (cons 50  3.17518655)
          (cons 51  4.71369369)
         )
         (list
          (cons 0 "ARC")
          (cons 100 "AcDbEntity")
          (cons 67 0)
          (cons 8 "0")
          (cons 62 1)
          (cons 6 "Continuous")
          (cons 100 "AcDbCircle")
          (list 10 -0.56844044 -0.20174776 0.00000000)
          (cons 40  0.00635000)
          (list 210 0.00000000 0.00000000 1.00000000)
          (cons 100 "AcDbArc")
          (cons 50  3.14159265)
          (cons 51  4.71238898)
         )
         (list
          (cons 0 "LINE")
          (cons 100 "AcDbEntity")
          (cons 67 0)
          (cons 8 "0")
          (cons 62 1)
          (cons 6 "Continuous")
          (cons 100 "AcDbLine")
          (list 10 -0.57479044 -0.20174776 0.00000000)
          (list 11 -0.57479044 -0.18625376 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.57948944 -0.19114998 0.00000000)
          (cons 40  0.00152400)
          (list 210 0.00000000 0.00000000 1.00000000)
          (cons 100 "AcDbArc")
          (cons 50  4.73738352)
          (cons 51  0.00000000)
         )
         (list
          (cons 0 "LINE")
          (cons 100 "AcDbEntity")
          (cons 67 0)
          (cons 8 "0")
          (cons 62 1)
          (cons 6 "Continuous")
          (cons 100 "AcDbLine")
          (list 10 -0.58245426 -0.18625376 0.00000000)
          (list 11 -0.58260074 -0.18640024 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.58357679 -0.18625376 0.00000000)
          (list 11 -0.58375205 -0.18642902 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.57948945 -0.18784694 0.00000000)
          (cons 40  0.00152401)
          (list 210 0.00000000 0.00000000 1.00000000)
          (cons 100 "AcDbArc")
          (cons 50  6.28317919)
          (cons 51  1.59579250)
         )
         (list
          (cons 0 "LINE")
          (cons 100 "AcDbEntity")
          (cons 67 0)
          (cons 8 "0")
          (cons 62 1)
          (cons 6 "Continuous")
          (cons 100 "AcDbLine")
          (list 10 -0.57796544 -0.18784695 0.00000000)
          (list 11 -0.57796544 -0.19114998 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.57796544 -0.18436603 0.00000000)
          (list 11 -0.57796544 -0.18628434 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 -0.57948945 -0.18436602 0.00000000)
          (cons 40  0.00152401)
          (list 210 0.00000000 0.00000000 1.00000000)
          (cons 100 "AcDbArc")
          (cons 50  6.28317861)
          (cons 51  1.27409195)
         )
         (list
          (cons 0 "LINE")
          (cons 100 "AcDbEntity")
          (cons 67 0)
          (cons 8 "0")
          (cons 62 1)
          (cons 6 "Continuous")
          (cons 100 "AcDbLine")
          (list 10 -0.56723394 -0.20809776 0.00000000)
          (list 11 -0.56844044 -0.20809776 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.56831344 -0.21673376 0.00000000)
          (list 11 -0.56831344 -0.21038376 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 -0.56723394 -0.21673376 0.00000000)
          (list 11 -0.56723394 -0.20809776 0.00000000)
          (list 210 0.00000000 0.00000000 1.00000000)
         )
         (list
          (cons 0 "ARC")
          (cons 100 "AcDbEntity")
          (cons 67 0)
          (cons 8 "0")
          (cons 62 1)
          (cons 100 "AcDbCircle")
          (list 10 -0.62454631 -0.15708173 0.00000000)
          (cons 40  0.01003300)
          (list 210 0.00000000 0.00000000 1.00000000)
          (cons 100 "AcDbArc")
          (cons 50  5.22075529)
          (cons 51  6.08794592)
         )
         (list
          (cons 0 "LINE")
          (cons 100 "AcDbEntity")
          (cons 67 0)
          (cons 8 "0")
          (cons 62 1)
          (cons 6 "Continuous")
          (cons 100 "AcDbLine")
          (list 10 -0.61430444 -0.15449611 0.00000000)
          (list 11 -0.61470350 -0.15902636 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.64235280 -0.35066986 0.00000000)
          (list 11 0.64235280 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.63272909 -0.35066986 0.00000000)
          (list 11 0.63272909 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.61348168 -0.35066986 0.00000000)
          (list 11 0.61348168 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.60385798 -0.33885393 0.00000000)
          (list 11 0.60385798 -0.35066986 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89942909 -0.35066986 0.00000000)
          (list 11 0.89942909 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90905280 -0.33885393 0.00000000)
          (list 11 0.90905280 -0.35066986 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.88018168 -0.35066986 0.00000000)
          (list 11 0.88018168 -0.33885393 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87055798 -0.35066986 0.00000000)
          (list 11 0.87055798 -0.33885393 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.62310539 -0.32459114 0.00000000)
          (cons 40  0.02779776)
          (list 210 0.00000000 0.00000000 1.00000000)
          (cons 100 "AcDbArc")
          (cons 50  4.35886680)
          (cons 51  5.06591116)
         )
         (list
          (cons 0 "LINE")
          (cons 100 "AcDbEntity")
          (cons 67 0)
          (cons 8 "0")
          (cons 62 1)
          (cons 6 "Continuous")
          (cons 100 "AcDbLine")
          (list 10 0.63754095 -0.35238896 0.00000000)
          (list 11 0.60866983 -0.35238896 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.60866983 -0.34479415 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 0.63754095 -0.34479415 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 0.88980539 -0.32459114 0.00000000)
          (cons 40  0.02779776)
          (list 210 0.00000000 0.00000000 1.00000000)
          (cons 100 "AcDbArc")
          (cons 50  4.35886680)
          (cons 51  5.06591116)
         )
         (list
          (cons 0 "LINE")
          (cons 100 "AcDbEntity")
          (cons 67 0)
          (cons 8 "0")
          (cons 62 1)
          (cons 6 "Continuous")
          (cons 100 "AcDbLine")
          (list 10 0.87536983 -0.35238896 0.00000000)
          (list 11 0.90424095 -0.35238896 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.87536983 -0.34479415 0.00000000)
          (cons 40  0.00759460)
          (list 210 0.00000000 0.00000000 1.00000000)
          (cons 100 "AcDbArc")
          (cons 50  4.02620608)
          (cons 51  5.39857188)
         )
         (list
          (cons 0 "ARC")
          (cons 100 "AcDbEntity")
          (cons 67 0)
          (cons 8 "0")
          (cons 62 1)
          (cons 100 "AcDbCircle")
          (list 10 0.90424095 -0.34479415 0.00000000)
          (cons 40  0.00759460)
          (list 210 0.00000000 0.00000000 1.00000000)
          (cons 100 "AcDbArc")
          (cons 50  4.02620608)
          (cons 51  5.39857188)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 0.87230539 -0.21980747 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.54627039 -0.21980747 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "LINE")
          (cons 100 "AcDbEntity")
          (cons 67 0)
          (cons 8 "0")
          (cons 62 1)
          (cons 6 "Continuous")
          (cons 100 "AcDbLine")
          (list 10 0.82598601 -0.16491097 0.00000000)
          (list 11 0.68706940 -0.17185683 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.69106555 -0.21470993 0.00000000)
          (list 11 0.75645539 -0.21470993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.80547178 -0.18489752 0.00000000)
          (list 11 0.70743900 -0.18489752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.80342294 -0.18794552 0.00000000)
          (list 11 0.70948781 -0.18794552 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.75645539 -0.21661493 0.00000000)
          (list 11 0.56398689 -0.21661493 0.00000000)
          (list 210 0.00000000 0.00000000 1.00000000)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 0.76419986 -0.12944852 0.00000000)
          (cons 40  0.00000000)
          (cons 41  0.00000000)
          (cons 42  -0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.75910098 -0.05347330 0.00000000)
          (cons 40  0.00000000)
          (cons 41  0.00000000)
          (cons 42  -0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.77259902 -0.03601235 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.78201498 -0.03315233 0.00000000)
          (cons 40  0.00000000)
          (cons 41  0.00000000)
          (cons 42  0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.78314548 -0.03150154 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.78156758 -0.01049529 0.00000000)
          (cons 40  0.00000000)
          (cons 41  0.00000000)
          (cons 42  0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.77528156 -0.00224490 0.00000000)
          (cons 40  0.00000000)
          (cons 41  0.00000000)
          (cons 42  0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.76292523 -0.00002067 0.00000000)
          (cons 40  0.00000000)
          (cons 41  0.00000000)
          (cons 42  0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.74704524 -0.00031747 0.00000000)
          (cons 40  0.00000000)
          (cons 41  0.00000000)
          (cons 42  0.01563647)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.73121484 -0.00160619 0.00000000)
          (cons 40  0.00000000)
          (cons 41  0.00000000)
          (cons 42  0.08294821)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71914201 -0.00505188 0.00000000)
          (cons 40  0.00000000)
          (cons 41  0.00000000)
          (cons 42  0.29629151)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71371033 -0.01388816 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71423569 -0.03494703 0.00000000)
          (cons 40  0.00000000)
          (cons 41  0.00000000)
          (cons 42  0.35117500)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.71552521 -0.03647682 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.72517949 -0.03838333 0.00000000)
          (cons 40  0.00000000)
          (cons 41  0.00000000)
          (cons 42  -0.31912861)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.74035195 -0.05441075 0.00000000)
          (cons 40  0.00000000)
          (cons 41  0.00000000)
          (cons 42  -0.05368786)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.74285708 -0.13051566 0.00000000)
          (cons 40  0.00000000)
          (cons 41  0.00000000)
          (cons 42  -0.30975875)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.72939626 -0.14732797 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68632615 -0.16041017 0.00000000)
          (cons 40  0.00000000)
          (cons 41  0.00000000)
          (cons 42  0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68519316 -0.16202101 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68560599 -0.17027766 0.00000000)
          (cons 40  0.00000000)
          (cons 41  0.00000000)
          (cons 42  0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.68728390 -0.17179576 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.75544874 -0.16838752 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82361359 -0.16497927 0.00000000)
          (cons 40  0.00000000)
          (cons 41  0.00000000)
          (cons 42  0.41421356)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82513169 -0.16330137 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82471886 -0.15504472 0.00000000)
          (cons 40  0.00000000)
          (cons 41  0.00000000)
          (cons 42  0.34416493)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.82343084 -0.15355494 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.77927059 -0.14483426 0.00000000)
          (cons 40  0.00000000)
          (cons 41  0.00000000)
          (cons 42  -0.30975875)
          (cons 91 0)
          (cons 70 0)
          (cons 50  0.00000000)
         )
         (list
          (cons 0 "SEQEND")
          (cons 100 "AcDbEntity")
          (cons 67 0)
          (cons 8 "0")
          (cons 62 1)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.59309019 -0.33161493 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.59309019 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.65312059 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.65312059 -0.33161493 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "ARC")
          (cons 100 "AcDbEntity")
          (cons 67 0)
          (cons 8 "0")
          (cons 62 1)
          (cons 6 "Continuous")
          (cons 100 "AcDbCircle")
          (list 10 0.65865480 -0.16339240 0.00000000)
          (cons 40  0.04795206)
          (list 210 0.00000000 0.00000000 1.00000000)
          (cons 100 "AcDbArc")
          (cons 50  1.58268281)
          (cons 51  2.79173224)
         )
         (list
          (cons 0 "ARC")
          (cons 100 "AcDbEntity")
          (cons 67 0)
          (cons 8 "0")
          (cons 62 1)
          (cons 100 "AcDbCircle")
          (list 10 0.62987989 -0.16187331 0.00000000)
          (cons 40  0.00317500)
          (list 210 0.00000000 0.00000000 1.00000000)
          (cons 100 "AcDbArc")
          (cons 50  4.76234514)
          (cons 51  6.06321256)
         )
         (list
          (cons 0 "ARC")
          (cons 100 "AcDbEntity")
          (cons 67 0)
          (cons 8 "0")
          (cons 62 1)
          (cons 100 "AcDbCircle")
          (list 10 0.62957955 -0.16341420 0.00000000)
          (cons 40  0.00317500)
          (list 210 0.00000000 0.00000000 1.00000000)
          (cons 100 "AcDbArc")
          (cons 50  4.76234816)
          (cons 51  6.11815870)
         )
         (list
          (cons 0 "ARC")
          (cons 100 "AcDbEntity")
          (cons 67 0)
          (cons 8 "0")
          (cons 62 1)
          (cons 100 "AcDbCircle")
          (list 10 0.62132441 -0.15696136 0.00000000)
          (cons 40  0.01003300)
          (list 210 0.00000000 0.00000000 1.00000000)
          (cons 100 "AcDbArc")
          (cons 50  5.32091457)
          (cons 51  6.18810520)
         )
         (list
          (cons 0 "ARC")
          (cons 100 "AcDbEntity")
          (cons 67 0)
          (cons 8 "0")
          (cons 62 1)
          (cons 100 "AcDbCircle")
          (list 10 0.62106561 -0.15366764 0.00000000)
          (cons 40  0.01003300)
          (list 210 0.00000000 0.00000000 1.00000000)
          (cons 100 "AcDbArc")
          (cons 50  6.27844057)
          (cons 51  3.21240381)
         )
         (list
          (cons 0 "LINE")
          (cons 100 "AcDbEntity")
          (cons 67 0)
          (cons 8 "0")
          (cons 62 1)
          (cons 6 "Continuous")
          (cons 100 "AcDbLine")
          (list 10 0.63316516 -0.17874828 0.00000000)
          (list 11 0.61919511 -0.17944678 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.65865475 -0.16339230 0.00000000)
          (cons 40  0.02788609)
          (list 210 0.00000000 0.00000000 1.00000000)
          (cons 100 "AcDbArc")
          (cons 50  1.37836689)
          (cons 51  2.94384873)
         )
         (list
          (cons 0 "LINE")
          (cons 100 "AcDbEntity")
          (cons 67 0)
          (cons 8 "0")
          (cons 62 1)
          (cons 6 "Continuous")
          (cons 100 "AcDbLine")
          (list 10 0.68501951 -0.19378752 0.00000000)
          (list 11 0.62551839 -0.19378752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.65804517 -0.18743752 0.00000000)
          (list 11 0.61928104 -0.18743752 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.61199285 -0.16747249 0.00000000)
          (cons 40  0.00152400)
          (list 210 0.00000000 0.00000000 1.00000000)
          (cons 100 "AcDbArc")
          (cons 50  1.62075249)
          (cons 51  3.10669405)
         )
         (list
          (cons 0 "LINE")
          (cons 100 "AcDbEntity")
          (cons 67 0)
          (cons 8 "0")
          (cons 62 1)
          (cons 6 "Continuous")
          (cons 100 "AcDbLine")
          (list 10 0.62973811 -0.16658524 0.00000000)
          (list 11 0.61186338 -0.16747899 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.56506639 -0.21026493 0.00000000)
          (list 11 0.62259739 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.56519339 -0.20162893 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 0.56398689 -0.21661493 0.00000000)
          (list 11 0.56398689 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.56506639 -0.21661493 0.00000000)
          (list 11 0.56506639 -0.21026493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.56398689 -0.20797893 0.00000000)
          (list 11 0.56519339 -0.20797893 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.61275489 -0.33161493 0.00000000)
          (list 11 0.61275489 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.61199289 -0.21661493 0.00000000)
          (list 11 0.61199289 -0.33161493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.60515592 -0.18613493 0.00000000)
          (list 11 0.57154339 -0.18613493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.60500774 -0.18692277 0.00000000)
          (list 11 0.57628049 -0.18620458 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57579682 -0.18278978 0.00000000)
          (list 11 0.60813570 -0.17290278 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.62551839 -0.19378752 0.00000000)
          (list 11 0.57620430 -0.19255468 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57154339 -0.20162893 0.00000000)
          (list 11 0.57154339 -0.18613493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.57624240 -0.18424720 0.00000000)
          (cons 40  0.00152401)
          (list 210 0.00000000 0.00000000 1.00000000)
          (cons 100 "AcDbArc")
          (cons 50  1.86750070)
          (cons 51  3.14159935)
         )
         (list
          (cons 0 "LINE")
          (cons 100 "AcDbEntity")
          (cons 67 0)
          (cons 8 "0")
          (cons 62 1)
          (cons 6 "Continuous")
          (cons 100 "AcDbLine")
          (list 10 0.57471839 -0.18424721 0.00000000)
          (list 11 0.57471839 -0.18616552 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57471839 -0.18772812 0.00000000)
          (list 11 0.57471839 -0.19103116 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.57624240 -0.18772811 0.00000000)
          (cons 40  0.00152401)
          (list 210 0.00000000 0.00000000 1.00000000)
          (cons 100 "AcDbArc")
          (cons 50  1.54580015)
          (cons 51  3.14159877)
         )
         (list
          (cons 0 "LINE")
          (cons 100 "AcDbEntity")
          (cons 67 0)
          (cons 8 "0")
          (cons 62 1)
          (cons 6 "Continuous")
          (cons 100 "AcDbLine")
          (list 10 0.58032973 -0.18613493 0.00000000)
          (list 11 0.58050499 -0.18631019 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.57920720 -0.18613493 0.00000000)
          (list 11 0.57935369 -0.18628142 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.57624239 -0.19103116 0.00000000)
          (cons 40  0.00152400)
          (list 210 0.00000000 0.00000000 1.00000000)
          (cons 100 "AcDbArc")
          (cons 50  3.14159265)
          (cons 51  4.68739444)
         )
         (list
          (cons 0 "ARC")
          (cons 100 "AcDbEntity")
          (cons 67 0)
          (cons 8 "0")
          (cons 62 1)
          (cons 6 "Continuous")
          (cons 100 "AcDbCircle")
          (list 10 0.60720742 -0.16986650 0.00000000)
          (cons 40  0.00317500)
          (list 210 0.00000000 0.00000000 1.00000000)
          (cons 100 "AcDbArc")
          (cons 50  5.00909736)
          (cons 51  6.24828930)
         )
         (list
          (cons 0 "ARC")
          (cons 100 "AcDbEntity")
          (cons 67 0)
          (cons 8 "0")
          (cons 62 1)
          (cons 6 "Continuous")
          (cons 100 "AcDbCircle")
          (list 10 0.61193948 -0.16900109 0.00000000)
          (cons 40  0.00152400)
          (list 210 0.00000000 0.00000000 1.00000000)
          (cons 100 "AcDbArc")
          (cons 50  1.62075550)
          (cons 51  3.10669405)
         )
         (list
          (cons 0 "ARC")
          (cons 100 "AcDbEntity")
          (cons 67 0)
          (cons 8 "0")
          (cons 62 1)
          (cons 100 "AcDbCircle")
          (list 10 0.61928103 -0.18438947 0.00000000)
          (cons 40  0.00304800)
          (list 210 0.00000000 0.00000000 1.00000000)
          (cons 100 "AcDbArc")
          (cons 50  3.10671132)
          (cons 51  4.71238864)
         )
         (list
          (cons 0 "LINE")
          (cons 100 "AcDbEntity")
          (cons 67 0)
          (cons 8 "0")
          (cons 62 1)
          (cons 6 "Continuous")
          (cons 100 "AcDbLine")
          (list 10 0.61630119 -0.18238462 0.00000000)
          (list 11 0.61623489 -0.18428317 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.61934731 -0.18249094 0.00000000)
          (cons 40  0.00304800)
          (list 210 0.00000000 0.00000000 1.00000000)
          (cons 100 "AcDbArc")
          (cons 50  1.62075668)
          (cons 51  3.10669273)
         )
         (list
          (cons 0 "ARC")
          (cons 100 "AcDbEntity")
          (cons 67 0)
          (cons 8 "0")
          (cons 62 1)
          (cons 100 "AcDbCircle")
          (list 10 0.60515592 -0.18130894 0.00000000)
          (cons 40  0.00482600)
          (list 210 0.00000000 0.00000000 1.00000000)
          (cons 100 "AcDbArc")
          (cons 50  4.71108427)
          (cons 51  6.24959141)
         )
         (list
          (cons 0 "ARC")
          (cons 100 "AcDbEntity")
          (cons 67 0)
          (cons 8 "0")
          (cons 62 1)
          (cons 6 "Continuous")
          (cons 100 "AcDbCircle")
          (list 10 0.60512835 -0.18209827 0.00000000)
          (cons 40  0.00482600)
          (list 210 0.00000000 0.00000000 1.00000000)
          (cons 100 "AcDbArc")
          (cons 50  4.68739405)
          (cons 51  6.24828671)
         )
         (list
          (cons 0 "LINE")
          (cons 100 "AcDbEntity")
          (cons 67 0)
          (cons 8 "0")
          (cons 62 1)
          (cons 6 "Continuous")
          (cons 100 "AcDbLine")
          (list 10 0.60995141 -0.18226666 0.00000000)
          (list 11 0.61046978 -0.16741932 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.62259739 -0.21026493 0.00000000)
          (list 11 0.62259739 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.61105738 -0.15437729 0.00000000)
          (list 11 0.61145644 -0.15890753 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.62129926 -0.15696291 0.00000000)
          (cons 40  0.01003300)
          (list 210 0.00000000 0.00000000 1.00000000)
          (cons 100 "AcDbArc")
          (cons 50  3.33683204)
          (cons 51  4.20402267)
         )
         (list
          (cons 0 "LINE")
          (cons 100 "AcDbEntity")
          (cons 67 0)
          (cons 8 "0")
          (cons 62 1)
          (cons 6 "Continuous")
          (cons 100 "AcDbLine")
          (list 10 0.63003844 -0.16504435 0.00000000)
          (list 11 0.61191675 -0.16595039 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.65776634 -0.16810846 0.00000000)
          (cons 40  0.01308100)
          (list 210 0.00000000 0.00000000 1.00000000)
          (cons 100 "AcDbArc")
          (cons 50  5.75958633)
          (cons 51  2.61799368)
         )
         (list
          (cons 0 "CIRCLE")
          (cons 100 "AcDbEntity")
          (cons 67 0)
          (cons 8 "0")
          (cons 62 1)
          (cons 100 "AcDbCircle")
          (list 10 0.65790463 -0.16505957 0.00000000)
          (cons 40  0.01003300)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68547138 -0.17041449 0.00000000)
          (list 11 0.68522731 -0.16575700 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.64643785 -0.16156798 0.00000000)
          (list 11 0.63834732 -0.17558121 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.68501951 -0.20166152 0.00000000)
          (cons 40  0.00787400)
          (list 210 0.00000000 0.00000000 1.00000000)
          (cons 100 "AcDbArc")
          (cons 50  0.05235824)
          (cons 51  1.57079633)
         )
         (list
          (cons 0 "ARC")
          (cons 100 "AcDbEntity")
          (cons 67 0)
          (cons 8 "0")
          (cons 62 1)
          (cons 6 "Continuous")
          (cons 100 "AcDbCircle")
          (list 10 0.69500280 -0.21242393 0.00000000)
          (cons 40  0.00228600)
          (list 210 0.00000000 0.00000000 1.00000000)
          (cons 100 "AcDbArc")
          (cons 50  3.19395433)
          (cons 51  4.71238898)
         )
         (list
          (cons 0 "LINE")
          (cons 100 "AcDbEntity")
          (cons 67 0)
          (cons 8 "0")
          (cons 62 1)
          (cons 6 "Continuous")
          (cons 100 "AcDbLine")
          (list 10 0.63421789 -0.21661493 0.00000000)
          (list 11 0.63421789 -0.33161493 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.63345589 -0.33161493 0.00000000)
          (list 11 0.63345589 -0.21661493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.65804517 -0.18108749 0.00000000)
          (cons 40  0.00635000)
          (list 210 0.00000000 0.00000000 1.00000000)
          (cons 100 "AcDbArc")
          (cons 50  4.71238756)
          (cons 51  5.75958441)
         )
         (list
          (cons 0 "LINE")
          (cons 100 "AcDbEntity")
          (cons 67 0)
          (cons 8 "0")
          (cons 62 1)
          (cons 6 "Continuous")
          (cons 100 "AcDbLine")
          (list 10 0.63834539 -0.21026493 0.00000000)
          (list 11 0.67523889 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.63284811 -0.17240608 0.00000000)
          (cons 40  0.00635000)
          (list 210 0.00000000 0.00000000 1.00000000)
          (cons 100 "AcDbArc")
          (cons 50  4.76234930)
          (cons 51  5.75958792)
         )
         (list
          (cons 0 "LINE")
          (cons 100 "AcDbEntity")
          (cons 67 0)
          (cons 8 "0")
          (cons 62 1)
          (cons 6 "Continuous")
          (cons 100 "AcDbLine")
          (list 10 0.63834539 -0.21026493 0.00000000)
          (list 11 0.63834539 -0.21661493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.68699328 -0.17033466 0.00000000)
          (cons 40  0.00152400)
          (list 210 0.00000000 0.00000000 1.00000000)
          (cons 100 "AcDbArc")
          (cons 50  3.19394659)
          (cons 51  4.76234498)
         )
         (list
          (cons 0 "ARC")
          (cons 100 "AcDbEntity")
          (cons 67 0)
          (cons 8 "0")
          (cons 62 1)
          (cons 6 "Continuous")
          (cons 100 "AcDbCircle")
          (list 10 0.69111131 -0.20310692 0.00000000)
          (cons 40  0.00111252)
          (list 210 0.00000000 0.00000000 1.00000000)
          (cons 100 "AcDbArc")
          (cons 50  0.05236168)
          (cons 51  3.10668488)
         )
         (list
          (cons 0 "LINE")
          (cons 100 "AcDbEntity")
          (cons 67 0)
          (cons 8 "0")
          (cons 62 1)
          (cons 6 "Continuous")
          (cons 100 "AcDbLine")
          (list 10 0.68158889 -0.20137493 0.00000000)
          (list 11 0.68158889 -0.20391493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68527189 -0.20137493 0.00000000)
          (list 11 0.68158889 -0.20137493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68793889 -0.20404193 0.00000000)
          (list 11 0.68793889 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.68527189 -0.20404193 0.00000000)
          (cons 40  0.00266700)
          (list 210 0.00000000 0.00000000 1.00000000)
          (cons 100 "AcDbArc")
          (cons 50  0.00000000)
          (cons 51  1.57079633)
         )
         (list
          (cons 0 "LINE")
          (cons 100 "AcDbEntity")
          (cons 67 0)
          (cons 8 "0")
          (cons 62 1)
          (cons 100 "AcDbLine")
          (list 10 0.68954155 -0.21623393 0.00000000)
          (list 11 0.68954155 -0.21661493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.69106555 -0.21623393 0.00000000)
          (cons 40  0.00152400)
          (list 210 0.00000000 0.00000000 1.00000000)
          (cons 100 "AcDbArc")
          (cons 50  1.57079633)
          (cons 51  3.14159265)
         )
         (list
          (cons 0 "ARC")
          (cons 100 "AcDbEntity")
          (cons 67 0)
          (cons 8 "0")
          (cons 62 1)
          (cons 6 "Continuous")
          (cons 100 "AcDbCircle")
          (list 10 0.68158889 -0.21026493 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 0.69271993 -0.21254358 0.00000000)
          (list 11 0.69222231 -0.20304870 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68999947 -0.20306809 0.00000000)
          (list 11 0.68952639 -0.21661493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.67523889 -0.20391493 0.00000000)
          (cons 40  0.00635000)
          (list 210 0.00000000 0.00000000 1.00000000)
          (cons 100 "AcDbArc")
          (cons 50  4.71238898)
          (cons 51  0.00000000)
         )
         (list
          (cons 0 "LINE")
          (cons 100 "AcDbEntity")
          (cons 67 0)
          (cons 8 "0")
          (cons 62 1)
          (cons 6 "Continuous")
          (cons 100 "AcDbLine")
          (list 10 0.66909481 -0.17464898 0.00000000)
          (list 11 0.66354442 -0.18426252 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.70743900 -0.18807251 0.00000000)
          (cons 40  0.00317500)
          (list 210 0.00000000 0.00000000 1.00000000)
          (cons 100 "AcDbArc")
          (cons 50  1.57079752)
          (cons 51  3.08923406)
         )
         (list
          (cons 0 "ARC")
          (cons 100 "AcDbEntity")
          (cons 67 0)
          (cons 8 "0")
          (cons 62 1)
          (cons 100 "AcDbCircle")
          (list 10 0.70374651 -0.21242393 0.00000000)
          (cons 40  0.00228600)
          (list 210 0.00000000 0.00000000 1.00000000)
          (cons 100 "AcDbArc")
          (cons 50  4.71238898)
          (cons 51  6.23082684)
         )
         (list
          (cons 0 "LINE")
          (cons 100 "AcDbEntity")
          (cons 67 0)
          (cons 8 "0")
          (cons 62 1)
          (cons 6 "Continuous")
          (cons 100 "AcDbLine")
          (list 10 0.70154217 -0.21232952 0.00000000)
          (list 11 0.69490961 -0.21232952 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.69338770 -0.21088528 0.00000000)
          (list 11 0.69288272 -0.20124944 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.70154217 -0.21080552 0.00000000)
          (cons 40  0.00152400)
          (list 210 0.00000000 0.00000000 1.00000000)
          (cons 100 "AcDbArc")
          (cons 50  4.71238898)
          (cons 51  6.23082584)
         )
         (list
          (cons 0 "LINE")
          (cons 100 "AcDbEntity")
          (cons 67 0)
          (cons 8 "0")
          (cons 62 1)
          (cons 6 "Continuous")
          (cons 100 "AcDbLine")
          (list 10 0.70306408 -0.21088528 0.00000000)
          (list 11 0.70426835 -0.18790636 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.69490961 -0.21080552 0.00000000)
          (cons 40  0.00152400)
          (list 210 0.00000000 0.00000000 1.00000000)
          (cons 100 "AcDbArc")
          (cons 50  3.19395089)
          (cons 51  4.71238898)
         )
         (list
          (cons 0 "ARC")
          (cons 100 "AcDbEntity")
          (cons 67 0)
          (cons 8 "0")
          (cons 62 1)
          (cons 6 "Continuous")
          (cons 100 "AcDbCircle")
          (list 10 0.70948781 -0.19023152 0.00000000)
          (cons 40  0.00228600)
          (list 210 0.00000000 0.00000000 1.00000000)
          (cons 100 "AcDbArc")
          (cons 50  1.57079633)
          (cons 51  3.08923419)
         )
         (list
          (cons 0 "LINE")
          (cons 100 "AcDbEntity")
          (cons 67 0)
          (cons 8 "0")
          (cons 62 1)
          (cons 6 "Continuous")
          (cons 100 "AcDbLine")
          (list 10 0.70602938 -0.21254357 0.00000000)
          (list 11 0.70720494 -0.19011189 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.65878123 -0.17258911 0.00000000)
          (cons 40  0.05715000)
          (list 210 0.00000000 0.00000000 1.00000000)
          (cons 100 "AcDbArc")
          (cons 50  0.57211891)
          (cons 51  1.58298294)
         )
         (list
          (cons 0 "LINE")
          (cons 100 "AcDbEntity")
          (cons 67 0)
          (cons 8 "0")
          (cons 62 1)
          (cons 6 "Continuous")
          (cons 100 "AcDbLine")
          (list 10 0.69060729 -0.15749575 0.00000000)
          (list 11 0.71120224 -0.15150935 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.68991805 -0.14579288 0.00000000)
          (list 11 0.70430932 -0.14161003 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.69425588 -0.15140957 0.00000000)
          (cons 40  0.00709676)
          (list 210 0.00000000 0.00000000 1.00000000)
          (cons 100 "AcDbArc")
          (cons 50  2.22842372)
          (cons 51  4.61698351)
         )
         (list
          (cons 0 "ARC")
          (cons 100 "AcDbEntity")
          (cons 67 0)
          (cons 8 "0")
          (cons 62 1)
          (cons 100 "AcDbCircle")
          (list 10 0.65776634 -0.16810846 0.00000000)
          (cons 40  0.02540001)
          (list 210 0.00000000 0.00000000 1.00000000)
          (cons 100 "AcDbArc")
          (cons 50  0.31756105)
          (cons 51  2.97656605)
         )
         (list
          (cons 0 "LINE")
          (cons 100 "AcDbEntity")
          (cons 67 0)
          (cons 8 "0")
          (cons 62 1)
          (cons 6 "Continuous")
          (cons 100 "AcDbLine")
          (list 10 0.63109428 -0.15337272 0.00000000)
          (list 11 0.63116276 -0.15892807 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.69251355 -0.15668763 0.00000000)
          (cons 40  0.01117600)
          (list 210 0.00000000 0.00000000 1.00000000)
          (cons 100 "AcDbArc")
          (cons 50  3.45914932)
          (cons 51  3.94597282)
         )
         (list
          (cons 0 "ARC")
          (cons 100 "AcDbEntity")
          (cons 67 0)
          (cons 8 "0")
          (cons 62 1)
          (cons 6 "Continuous")
          (cons 100 "AcDbCircle")
          (list 10 0.68370540 -0.16583676 0.00000000)
          (cons 40  0.00152400)
          (list 210 0.00000000 0.00000000 1.00000000)
          (cons 100 "AcDbArc")
          (cons 50  0.05237527)
          (cons 51  0.80439198)
         )
         (list
          (cons 0 "ARC")
          (cons 100 "AcDbEntity")
          (cons 67 0)
          (cons 8 "0")
          (cons 62 1)
          (cons 100 "AcDbCircle")
          (list 10 0.65689584 -0.17242039 0.00000000)
          (cons 40  0.03708400)
          (list 210 0.00000000 0.00000000 1.00000000)
          (cons 100 "AcDbArc")
          (cons 50  0.61563997)
          (cons 51  1.37836895)
         )
         (list
          (cons 0 "ARC")
          (cons 100 "AcDbEntity")
          (cons 67 0)
          (cons 8 "0")
          (cons 62 1)
          (cons 6 "Continuous")
          (cons 100 "AcDbCircle")
          (list 10 0.70547342 -0.14814883 0.00000000)
          (cons 40  0.00664164)
          (list 210 0.00000000 0.00000000 1.00000000)
          (cons 100 "AcDbArc")
          (cons 50  5.25931137)
          (cons 51  1.74699270)
         )
         (list
          (cons 0 "POLYLINE")
          (cons 100 "AcDbEntity")
          (cons 67 0)
          (cons 8 "0")
          (cons 62 1)
          (cons 6 "Continuous")
          (cons 100 "AcDb2dPolyline")
          (cons 66 1)
          (list 10 0.00000000 0.00000000 0.00000000)
          (cons 70 1)
          (cons 40  0.00000000)
          (cons 41  0.00000000)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.91982059 -0.33161493 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.91982059 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.85979019 -0.33885393 0.00000000)
          (cons 40  0.00000000)
          (cons 41  0.00000000)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 6 "Continuous")
          (cons 100 "AcDbVertex")
          (cons 100 "AcDb2dVertex")
          (list 10 0.85979019 -0.33161493 0.00000000)
          (cons 40  0.00000000)
          (cons 41  0.00000000)
          (cons 42  0.00000000)
          (cons 91 0)
          (cons 70 0)
          (cons 50  0.00000000)
         )
         (list
          (cons 0 "SEQEND")
          (cons 100 "AcDbEntity")
          (cons 67 0)
          (cons 8 "0")
          (cons 62 1)
          (cons 6 "Continuous")
         )
         (list
          (cons 0 "LINE")
          (cons 100 "AcDbEntity")
          (cons 67 0)
          (cons 8 "0")
          (cons 62 1)
          (cons 6 "Continuous")
          (cons 100 "AcDbLine")
          (list 10 0.94892389 -0.21661493 0.00000000)
          (list 11 0.75645539 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90982059 -0.20073993 0.00000000)
          (list 11 0.86979019 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.85005439 -0.20797893 0.00000000)
          (list 11 0.94892389 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90982059 -0.20797893 0.00000000)
          (list 11 0.86979019 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.83767189 -0.21026493 0.00000000)
          (list 11 0.94784439 -0.21026493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.89122805 -0.14499137 0.00000000)
          (cons 40  0.01003300)
          (list 210 0.00000000 0.00000000 1.00000000)
          (cons 100 "AcDbArc")
          (cons 50  3.38794173)
          (cons 51  4.20388555)
         )
         (list
          (cons 0 "ARC")
          (cons 100 "AcDbEntity")
          (cons 67 0)
          (cons 8 "0")
          (cons 62 1)
          (cons 100 "AcDbCircle")
          (list 10 0.85430384 -0.15361429 0.00000000)
          (cons 40  0.02788666)
          (list 210 0.00000000 0.00000000 1.00000000)
          (cons 100 "AcDbArc")
          (cons 50  0.22332772)
          (cons 51  0.66810518)
         )
         (list
          (cons 0 "ARC")
          (cons 100 "AcDbEntity")
          (cons 67 0)
          (cons 8 "0")
          (cons 62 1)
          (cons 6 "Continuous")
          (cons 100 "AcDbCircle")
          (list 10 0.88220234 -0.15078302 0.00000000)
          (cons 40  0.00317500)
          (list 210 0.00000000 0.00000000 1.00000000)
          (cons 100 "AcDbArc")
          (cons 50  3.40653662)
          (cons 51  4.76234402)
         )
         (list
          (cons 0 "ARC")
          (cons 100 "AcDbEntity")
          (cons 67 0)
          (cons 8 "0")
          (cons 62 1)
          (cons 6 "Continuous")
          (cons 100 "AcDbCircle")
          (list 10 0.88256789 -0.15229066 0.00000000)
          (cons 40  0.00317500)
          (list 210 0.00000000 0.00000000 1.00000000)
          (cons 100 "AcDbArc")
          (cons 50  3.35223205)
          (cons 51  4.76236200)
         )
         (list
          (cons 0 "LINE")
          (cons 100 "AcDbEntity")
          (cons 67 0)
          (cons 8 "0")
          (cons 62 1)
          (cons 6 "Continuous")
          (cons 100 "AcDbLine")
          (list 10 0.89280813 -0.16729199 0.00000000)
          (list 11 0.87931773 -0.16796652 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.90091789 -0.17031082 0.00000000)
          (list 11 0.87869289 -0.17031082 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87536983 -0.18720491 0.00000000)
          (list 11 0.90424095 -0.18720491 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.88980539 -0.21500273 0.00000000)
          (cons 40  0.02779776)
          (list 210 0.00000000 0.00000000 1.00000000)
          (cons 100 "AcDbArc")
          (cons 50  1.21727415)
          (cons 51  1.92431851)
         )
         (list
          (cons 0 "ARC")
          (cons 100 "AcDbEntity")
          (cons 67 0)
          (cons 8 "0")
          (cons 62 1)
          (cons 100 "AcDbCircle")
          (list 10 0.85430396 -0.15361449 0.00000000)
          (cons 40  0.04795266)
          (list 210 0.00000000 0.00000000 1.00000000)
          (cons 100 "AcDbArc")
          (cons 50  0.27024809)
          (cons 51  1.68983637)
         )
         (list
          (cons 0 "ARC")
          (cons 100 "AcDbEntity")
          (cons 67 0)
          (cons 8 "0")
          (cons 62 1)
          (cons 6 "Continuous")
          (cons 100 "AcDbCircle")
          (list 10 0.87900063 -0.16162444 0.00000000)
          (cons 40  0.00635001)
          (list 210 0.00000000 0.00000000 1.00000000)
          (cons 100 "AcDbArc")
          (cons 50  3.66518929)
          (cons 51  4.76234710)
         )
         (list
          (cons 0 "LINE")
          (cons 100 "AcDbEntity")
          (cons 67 0)
          (cons 8 "0")
          (cons 62 1)
          (cons 6 "Continuous")
          (cons 100 "AcDbLine")
          (list 10 0.84383139 -0.20162893 0.00000000)
          (list 11 0.84383139 -0.16573350 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.84011118 -0.15869308 0.00000000)
          (list 11 0.84128161 -0.19221034 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.84329591 -0.16480602 0.00000000)
          (list 11 0.85452911 -0.18426252 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82184616 -0.21470993 0.00000000)
          (list 11 0.75645539 -0.21470993 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.81790801 -0.21242327 0.00000000)
          (cons 40  0.00228600)
          (list 210 0.00000000 0.00000000 1.00000000)
          (cons 100 "AcDbArc")
          (cons 50  4.71239007)
          (cons 51  6.23084044)
         )
         (list
          (cons 0 "ARC")
          (cons 100 "AcDbEntity")
          (cons 67 0)
          (cons 8 "0")
          (cons 62 1)
          (cons 6 "Continuous")
          (cons 100 "AcDbCircle")
          (list 10 0.81800117 -0.21080552 0.00000000)
          (cons 40  0.00152400)
          (list 210 0.00000000 0.00000000 1.00000000)
          (cons 100 "AcDbArc")
          (cons 50  4.71239106)
          (cons 51  6.23083033)
         )
         (list
          (cons 0 "ARC")
          (cons 100 "AcDbEntity")
          (cons 67 0)
          (cons 8 "0")
          (cons 62 1)
          (cons 6 "Continuous")
          (cons 100 "AcDbCircle")
          (list 10 0.80547178 -0.18807253 0.00000000)
          (cons 40  0.00317500)
          (list 210 0.00000000 0.00000000 1.00000000)
          (cons 100 "AcDbArc")
          (cons 50  0.05236109)
          (cons 51  1.57079763)
         )
         (list
          (cons 0 "ARC")
          (cons 100 "AcDbEntity")
          (cons 67 0)
          (cons 8 "0")
          (cons 62 1)
          (cons 6 "Continuous")
          (cons 100 "AcDbCircle")
          (list 10 0.80342294 -0.19023152 0.00000000)
          (cons 40  0.00228600)
          (list 210 0.00000000 0.00000000 1.00000000)
          (cons 100 "AcDbArc")
          (cons 50  0.05235960)
          (cons 51  1.57079633)
         )
         (list
          (cons 0 "LINE")
          (cons 100 "AcDbEntity")
          (cons 67 0)
          (cons 8 "0")
          (cons 62 1)
          (cons 6 "Continuous")
          (cons 100 "AcDbLine")
          (list 10 0.81800116 -0.21232952 0.00000000)
          (list 11 0.81136861 -0.21232952 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.81136861 -0.21080552 0.00000000)
          (cons 40  0.00152400)
          (list 210 0.00000000 0.00000000 1.00000000)
          (cons 100 "AcDbArc")
          (cons 50  3.19395164)
          (cons 51  4.71239091)
         )
         (list
          (cons 0 "ARC")
          (cons 100 "AcDbEntity")
          (cons 67 0)
          (cons 8 "0")
          (cons 62 1)
          (cons 6 "Continuous")
          (cons 100 "AcDbCircle")
          (list 10 0.80916427 -0.21242393 0.00000000)
          (cons 40  0.00228600)
          (list 210 0.00000000 0.00000000 1.00000000)
          (cons 100 "AcDbArc")
          (cons 50  3.19395164)
          (cons 51  4.71239091)
         )
         (list
          (cons 0 "LINE")
          (cons 100 "AcDbEntity")
          (cons 67 0)
          (cons 8 "0")
          (cons 62 1)
          (cons 6 "Continuous")
          (cons 100 "AcDbLine")
          (list 10 0.80688140 -0.21254357 0.00000000)
          (list 11 0.80570581 -0.19011188 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.80984670 -0.21088528 0.00000000)
          (list 11 0.80864243 -0.18790636 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.87945489 -0.33161493 0.00000000)
          (list 11 0.87945489 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87869289 -0.21661493 0.00000000)
          (list 11 0.87869289 -0.33161493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.85018139 -0.20162893 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 6 "Continuous")
          (cons 100 "AcDbCircle")
          (list 10 0.82789129 -0.20166171 0.00000000)
          (cons 40  0.00787400)
          (list 210 0.00000000 0.00000000 1.00000000)
          (cons 100 "AcDbArc")
          (cons 50  1.57079658)
          (cons 51  3.08923025)
         )
         (list
          (cons 0 "ARC")
          (cons 100 "AcDbEntity")
          (cons 67 0)
          (cons 8 "0")
          (cons 62 1)
          (cons 100 "AcDbCircle")
          (list 10 0.83132189 -0.21026493 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 6 "Continuous")
          (cons 100 "AcDbCircle")
          (list 10 0.82763889 -0.20404193 0.00000000)
          (cons 40  0.00266700)
          (list 210 0.00000000 0.00000000 1.00000000)
          (cons 100 "AcDbArc")
          (cons 50  1.57079633)
          (cons 51  3.14159265)
         )
         (list
          (cons 0 "ARC")
          (cons 100 "AcDbEntity")
          (cons 67 0)
          (cons 8 "0")
          (cons 62 1)
          (cons 6 "Continuous")
          (cons 100 "AcDbCircle")
          (list 10 0.82179946 -0.20310692 0.00000000)
          (cons 40  0.00111252)
          (list 210 0.00000000 0.00000000 1.00000000)
          (cons 100 "AcDbArc")
          (cons 50  0.03490778)
          (cons 51  3.08923097)
         )
         (list
          (cons 0 "ARC")
          (cons 100 "AcDbEntity")
          (cons 67 0)
          (cons 8 "0")
          (cons 62 1)
          (cons 6 "Continuous")
          (cons 100 "AcDbCircle")
          (list 10 0.82184616 -0.21623393 0.00000000)
          (cons 40  0.00152399)
          (list 210 0.00000000 0.00000000 1.00000000)
          (cons 100 "AcDbArc")
          (cons 50  0.03490348)
          (cons 51  1.57079246)
         )
         (list
          (cons 0 "LINE")
          (cons 100 "AcDbEntity")
          (cons 67 0)
          (cons 8 "0")
          (cons 62 1)
          (cons 6 "Continuous")
          (cons 100 "AcDbLine")
          (list 10 0.81952308 -0.21088528 0.00000000)
          (list 11 0.82002806 -0.20124943 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82019085 -0.21254357 0.00000000)
          (list 11 0.82068847 -0.20304870 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82291131 -0.20306809 0.00000000)
          (list 11 0.82338439 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.83132189 -0.20137493 0.00000000)
          (list 11 0.83132189 -0.20391493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.83132189 -0.20137493 0.00000000)
          (list 11 0.82763889 -0.20137493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.83975854 -0.19226352 0.00000000)
          (cons 40  0.00152400)
          (list 210 0.00000000 0.00000000 1.00000000)
          (cons 100 "AcDbArc")
          (cons 50  4.71238898)
          (cons 51  0.03490610)
         )
         (list
          (cons 0 "LINE")
          (cons 100 "AcDbEntity")
          (cons 67 0)
          (cons 8 "0")
          (cons 62 1)
          (cons 6 "Continuous")
          (cons 100 "AcDbLine")
          (list 10 0.83975854 -0.19378752 0.00000000)
          (list 11 0.82789129 -0.19378752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.82497189 -0.20404193 0.00000000)
          (list 11 0.82497189 -0.21026493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.83767189 -0.20391493 0.00000000)
          (cons 40  0.00635000)
          (list 210 0.00000000 0.00000000 1.00000000)
          (cons 100 "AcDbArc")
          (cons 50  3.14159265)
          (cons 51  4.71238898)
         )
         (list
          (cons 0 "ARC")
          (cons 100 "AcDbEntity")
          (cons 67 0)
          (cons 8 "0")
          (cons 62 1)
          (cons 100 "AcDbCircle")
          (list 10 0.87536983 -0.19479972 0.00000000)
          (cons 40  0.00759460)
          (list 210 0.00000000 0.00000000 1.00000000)
          (cons 100 "AcDbArc")
          (cons 50  0.88461343)
          (cons 51  2.25697923)
         )
         (list
          (cons 0 "ARC")
          (cons 100 "AcDbEntity")
          (cons 67 0)
          (cons 8 "0")
          (cons 62 1)
          (cons 6 "Continuous")
          (cons 100 "AcDbCircle")
          (list 10 0.86002837 -0.18108751 0.00000000)
          (cons 40  0.00635001)
          (list 210 0.00000000 0.00000000 1.00000000)
          (cons 100 "AcDbArc")
          (cons 50  3.66519208)
          (cons 51  4.71239093)
         )
         (list
          (cons 0 "LINE")
          (cons 100 "AcDbEntity")
          (cons 67 0)
          (cons 8 "0")
          (cons 62 1)
          (cons 6 "Continuous")
          (cons 100 "AcDbLine")
          (list 10 0.87055798 -0.18743752 0.00000000)
          (list 11 0.86002838 -0.18743752 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87055798 -0.18892401 0.00000000)
          (list 11 0.87055798 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.86188810 -0.21026493 0.00000000)
          (list 11 0.86188810 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.85488039 -0.21026493 0.00000000)
          (list 11 0.85488039 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.85005439 -0.20797766 0.00000000)
          (list 11 0.85005439 -0.21026493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.86979019 -0.20073993 0.00000000)
          (list 11 0.86979019 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.88018168 -0.18892401 0.00000000)
          (list 11 0.88018168 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.87869289 -0.17031082 0.00000000)
          (list 11 0.87869289 -0.18720491 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.87945489 -0.18720491 0.00000000)
          (list 11 0.87945489 -0.17031082 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.85537964 -0.16274952 0.00000000)
          (cons 40  0.05715000)
          (list 210 0.00000000 0.00000000 1.00000000)
          (cons 100 "AcDbArc")
          (cons 50  1.68955122)
          (cons 51  2.74425538)
         )
         (list
          (cons 0 "ARC")
          (cons 100 "AcDbEntity")
          (cons 67 0)
          (cons 8 "0")
          (cons 62 1)
          (cons 100 "AcDbCircle")
          (list 10 0.80741348 -0.14343886 0.00000000)
          (cons 40  0.00664210)
          (list 210 0.00000000 0.00000000 1.00000000)
          (cons 100 "AcDbArc")
          (cons 50  2.11288665)
          (cons 51  4.40122392)
         )
         (list
          (cons 0 "ARC")
          (cons 100 "AcDbEntity")
          (cons 67 0)
          (cons 8 "0")
          (cons 62 1)
          (cons 100 "AcDbCircle")
          (list 10 0.85462441 -0.15826551 0.00000000)
          (cons 40  0.02540000)
          (list 210 0.00000000 0.00000000 1.00000000)
          (cons 100 "AcDbArc")
          (cons 50  0.26494369)
          (cons 51  2.96093612)
         )
         (list
          (cons 0 "ARC")
          (cons 100 "AcDbEntity")
          (cons 67 0)
          (cons 8 "0")
          (cons 62 1)
          (cons 100 "AcDbCircle")
          (list 10 0.85430391 -0.15361452 0.00000000)
          (cons 40  0.02788666)
          (list 210 0.00000000 0.00000000 1.00000000)
          (cons 100 "AcDbArc")
          (cons 50  0.66810459)
          (cons 51  1.89415366)
         )
         (list
          (cons 0 "ARC")
          (cons 100 "AcDbEntity")
          (cons 67 0)
          (cons 8 "0")
          (cons 62 1)
          (cons 6 "Continuous")
          (cons 100 "AcDbCircle")
          (list 10 0.85462440 -0.15826551 0.00000000)
          (cons 40  0.01308100)
          (list 210 0.00000000 0.00000000 1.00000000)
          (cons 100 "AcDbArc")
          (cons 50  0.52359898)
          (cons 51  3.66519163)
         )
         (list
          (cons 0 "ARC")
          (cons 100 "AcDbEntity")
          (cons 67 0)
          (cons 8 "0")
          (cons 62 1)
          (cons 100 "AcDbCircle")
          (list 10 0.85462438 -0.15302720 0.00000000)
          (cons 40  0.01008126)
          (list 210 0.00000000 0.00000000 1.00000000)
          (cons 100 "AcDbArc")
          (cons 50  0.40917396)
          (cons 51  2.73241933)
         )
         (list
          (cons 0 "CIRCLE")
          (cons 100 "AcDbEntity")
          (cons 67 0)
          (cons 8 "0")
          (cons 62 1)
          (cons 100 "AcDbCircle")
          (list 10 0.85481283 -0.15521891 0.00000000)
          (cons 40  0.01003300)
          (list 210 0.00000000 0.00000000 1.00000000)
         )
         (list
          (cons 0 "ARC")
          (cons 100 "AcDbEntity")
          (cons 67 0)
          (cons 8 "0")
          (cons 62 1)
          (cons 100 "AcDbCircle")
          (list 10 0.85722691 -0.16233550 0.00000000)
          (cons 40  0.03708400)
          (list 210 0.00000000 0.00000000 1.00000000)
          (cons 100 "AcDbArc")
          (cons 50  1.89416688)
          (cons 51  2.66089606)
         )
         (list
          (cons 0 "ARC")
          (cons 100 "AcDbEntity")
          (cons 67 0)
          (cons 8 "0")
          (cons 62 1)
          (cons 6 "Continuous")
          (cons 100 "AcDbCircle")
          (list 10 0.81887093 -0.14571570 0.00000000)
          (cons 40  0.00709647)
          (list 210 0.00000000 0.00000000 1.00000000)
          (cons 100 "AcDbArc")
          (cons 50  4.90386054)
          (cons 51  0.36939896)
         )
         (list
          (cons 0 "ARC")
          (cons 100 "AcDbEntity")
          (cons 67 0)
          (cons 8 "0")
          (cons 62 1)
          (cons 6 "Continuous")
          (cons 100 "AcDbCircle")
          (list 10 0.82590989 -0.16338886 0.00000000)
          (cons 40  0.00152400)
          (list 210 0.00000000 0.00000000 1.00000000)
          (cons 100 "AcDbArc")
          (cons 50  4.76235952)
          (cons 51  6.23082712)
         )
         (list
          (cons 0 "LINE")
          (cons 100 "AcDbEntity")
          (cons 67 0)
          (cons 8 "0")
          (cons 62 1)
          (cons 6 "Continuous")
          (cons 100 "AcDbLine")
          (list 10 0.82743180 -0.16346863 0.00000000)
          (list 11 0.82768347 -0.15866651 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.82920538 -0.15874627 0.00000000)
          (cons 40  0.00152400)
          (list 210 0.00000000 0.00000000 1.00000000)
          (cons 100 "AcDbArc")
          (cons 50  1.57079220)
          (cons 51  3.08923426)
         )
         (list
          (cons 0 "ARC")
          (cons 100 "AcDbEntity")
          (cons 67 0)
          (cons 8 "0")
          (cons 62 1)
          (cons 6 "Continuous")
          (cons 100 "AcDbCircle")
          (list 10 0.83858811 -0.15874626 0.00000000)
          (cons 40  0.00152399)
          (list 210 0.00000000 0.00000000 1.00000000)
          (cons 100 "AcDbArc")
          (cons 50  0.03490348)
          (cons 51  1.57079246)
         )
         (list
          (cons 0 "LINE")
          (cons 100 "AcDbEntity")
          (cons 67 0)
          (cons 8 "0")
          (cons 62 1)
          (cons 6 "Continuous")
          (cons 100 "AcDbLine")
          (list 10 0.84158506 -0.15722227 0.00000000)
          (list 11 0.82920538 -0.15722227 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.84158506 -0.15722227 0.00000000)
          (list 11 0.82920538 -0.15722227 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.81864363 -0.15169362 0.00000000)
          (cons 40  0.01117600)
          (list 210 0.00000000 0.00000000 1.00000000)
          (cons 100 "AcDbArc")
          (cons 50  5.69443002)
          (cons 51  6.10252135)
         )
         (list
          (cons 0 "LINE")
          (cons 100 "AcDbEntity")
          (cons 67 0)
          (cons 8 "0")
          (cons 62 1)
          (cons 6 "Continuous")
          (cons 100 "AcDbLine")
          (list 10 0.82747638 -0.16261806 0.00000000)
          (list 11 0.83287215 -0.15722227 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.86595286 -0.15172502 0.00000000)
          (list 11 0.87350136 -0.16479944 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.87025699 -0.15918003 0.00000000)
          (list 11 0.85899105 -0.16434049 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.87500755 -0.13493306 0.00000000)
          (list 11 0.86931135 -0.13754224 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.90533009 -0.16429228 0.00000000)
          (cons 40  0.00317500)
          (list 210 0.00000000 0.00000000 1.00000000)
          (cons 100 "AcDbArc")
          (cons 50  3.17649516)
          (cons 51  4.27604392)
         )
         (list
          (cons 0 "ARC")
          (cons 100 "AcDbEntity")
          (cons 67 0)
          (cons 8 "0")
          (cons 62 1)
          (cons 100 "AcDbCircle")
          (list 10 0.89296037 -0.17033727 0.00000000)
          (cons 40  0.00304800)
          (list 210 0.00000000 0.00000000 1.00000000)
          (cons 100 "AcDbArc")
          (cons 50  0.03525777)
          (cons 51  1.62074685)
         )
         (list
          (cons 0 "LINE")
          (cons 100 "AcDbEntity")
          (cons 67 0)
          (cons 8 "0")
          (cons 62 1)
          (cons 6 "Continuous")
          (cons 100 "AcDbLine")
          (list 10 0.90181212 -0.15453037 0.00000000)
          (list 11 0.90291574 -0.18613493 0.00000000)
          (list 210 0.00000000 0.00000000 1.00000000)
         )
         (list
          (cons 0 "ARC")
          (cons 100 "AcDbEntity")
          (cons 67 0)
          (cons 8 "0")
          (cons 62 1)
          (cons 6 "Continuous")
          (cons 100 "AcDbCircle")
          (list 10 0.94771739 -0.20162893 0.00000000)
          (cons 40  0.00635000)
          (list 210 0.00000000 0.00000000 1.00000000)
          (cons 100 "AcDbArc")
          (cons 50  3.14159265)
          (cons 51  4.71238898)
         )
         (list
          (cons 0 "POLYLINE")
          (cons 100 "AcDbEntity")
          (cons 67 0)
          (cons 8 "0")
          (cons 62 1)
          (cons 100 "AcDb2dPolyline")
          (cons 66 1)
          (list 10 0.00000000 0.00000000 0.00000000)
          (cons 70 0)
          (cons 40  0.00638500)
          (cons 41  0.00638500)
          (list 210 0.00000000 0.00000000 1.00000000)
          (cons 71 0)
          (cons 72 0)
          (cons 73 0)
          (cons 74 0)
          (cons 75 0)
         )
         (list
          (cons 0 "VERTEX")
          (cons 100 "AcDbEntity")
          (cons 67 0)
          (cons 8 "0")
          (cons 62 1)
          (cons 100 "AcDbVertex")
          (cons 100 "AcDb2dVertex")
          (list 10 0.96664039 -0.21980747 0.00000000)
          (cons 40  0.00638500)
          (cons 41  0.00638500)
          (cons 42  0.00000000)
          (cons 91 0)
          (cons 70 0)
          (cons 50  0.00000000)
         )
         (list
          (cons 0 "VERTEX")
          (cons 100 "AcDbEntity")
          (cons 67 0)
          (cons 8 "0")
          (cons 62 1)
          (cons 100 "AcDbVertex")
          (cons 100 "AcDb2dVertex")
          (list 10 0.90730539 -0.21980747 0.00000000)
          (cons 40  0.00638500)
          (cons 41  0.00638500)
          (cons 42  0.00000000)
          (cons 91 0)
          (cons 70 0)
          (cons 50  0.00000000)
         )
         (list
          (cons 0 "SEQEND")
          (cons 100 "AcDbEntity")
          (cons 67 0)
          (cons 8 "0")
          (cons 62 1)
         )
         (list
          (cons 0 "LINE")
          (cons 100 "AcDbEntity")
          (cons 67 0)
          (cons 8 "0")
          (cons 62 1)
          (cons 6 "DASHED")
          (cons 100 "AcDbLine")
          (list 10 0.90015589 -0.33161493 0.00000000)
          (list 11 0.90015589 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90091789 -0.21661493 0.00000000)
          (list 11 0.90091789 -0.33161493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94136739 -0.18613493 0.00000000)
          (list 11 0.90091789 -0.18613493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.93731246 -0.18270921 0.00000000)
          (list 11 0.90398811 -0.16716980 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89600647 -0.17022983 0.00000000)
          (list 11 0.89600930 -0.17031082 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89942909 -0.18892401 0.00000000)
          (list 11 0.89942909 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90905280 -0.20073993 0.00000000)
          (list 11 0.90905280 -0.18892401 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.90424095 -0.19479972 0.00000000)
          (cons 40  0.00759460)
          (list 210 0.00000000 0.00000000 1.00000000)
          (cons 100 "AcDbArc")
          (cons 50  0.88461343)
          (cons 51  2.25697923)
         )
         (list
          (cons 0 "LINE")
          (cons 100 "AcDbEntity")
          (cons 67 0)
          (cons 8 "0")
          (cons 62 1)
          (cons 6 "Continuous")
          (cons 100 "AcDbLine")
          (list 10 0.90091789 -0.17031082 0.00000000)
          (list 11 0.90091789 -0.18720491 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.90015589 -0.18720491 0.00000000)
          (list 11 0.90015589 -0.17031082 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90982059 -0.20073993 0.00000000)
          (list 11 0.90982059 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89450253 -0.20797893 0.00000000)
          (list 11 0.88726353 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.89234724 -0.20797893 0.00000000)
          (list 11 0.88510824 -0.20073993 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94136739 -0.20162893 0.00000000)
          (list 11 0.94136739 -0.18613493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.93819239 -0.18409041 0.00000000)
          (list 11 0.93819239 -0.18613493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.93666839 -0.18409042 0.00000000)
          (cons 40  0.00152400)
          (list 210 0.00000000 0.00000000 1.00000000)
          (cons 100 "AcDbArc")
          (cons 50  0.00000668)
          (cons 51  1.13446471)
         )
         (list
          (cons 0 "LINE")
          (cons 100 "AcDbEntity")
          (cons 67 0)
          (cons 8 "0")
          (cons 62 1)
          (cons 6 "Continuous")
          (cons 100 "AcDbLine")
          (list 10 0.91772268 -0.21026493 0.00000000)
          (list 11 0.91772268 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.92473039 -0.21026493 0.00000000)
          (list 11 0.92473039 -0.21661493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.92955639 -0.20797893 0.00000000)
          (list 11 0.92955639 -0.21026493 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94892389 -0.21661493 0.00000000)
          (list 11 0.94892389 -0.20797893 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94869186 -0.21661493 0.00000000)
          (list 11 0.94784439 -0.21576746 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.94784439 -0.21661493 0.00000000)
          (list 11 0.94784439 -0.21026493 0.00000000)
          (list 210 0.00000000 0.00000000 1.00000000)
         )
         (list
          (cons 0 "ARC")
          (cons 100 "AcDbEntity")
          (cons 67 0)
          (cons 8 "0")
          (cons 62 1)
          (cons 100 "AcDbCircle")
          (list 10 0.89122805 -0.14499137 0.00000000)
          (cons 40  0.01003300)
          (list 210 0.00000000 0.00000000 1.00000000)
          (cons 100 "AcDbArc")
          (cons 50  5.32080678)
          (cons 51  0.21754705)
         )
         (list
          (cons 0 "ARC")
          (cons 100 "AcDbEntity")
          (cons 67 0)
          (cons 8 "0")
          (cons 62 1)
          (cons 6 "Continuous")
          (cons 100 "AcDbCircle")
          (list 10 0.90034257 -0.15610679 0.00000000)
          (cons 40  0.00152400)
          (list 210 0.00000000 0.00000000 1.00000000)
          (cons 100 "AcDbArc")
          (cons 50  0.03490194)
          (cons 51  1.62078222)
         )
         (list
          (cons 0 "ARC")
          (cons 100 "AcDbEntity")
          (cons 67 0)
          (cons 8 "0")
          (cons 62 1)
          (cons 100 "AcDbCircle")
          (list 10 0.90028905 -0.15458361 0.00000000)
          (cons 40  0.00152400)
          (list 210 0.00000000 0.00000000 1.00000000)
          (cons 100 "AcDbArc")
          (cons 50  0.03491231)
          (cons 51  1.62075305)
         )
         (list
          (cons 0 "LINE")
          (cons 100 "AcDbEntity")
          (cons 67 0)
          (cons 8 "0")
          (cons 62 1)
          (cons 6 "Continuous")
          (cons 100 "AcDbLine")
          (list 10 0.90051598 -0.14081364 0.00000000)
          (list 11 0.90101827 -0.14282910 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.88466544 -0.15258011 0.00000000)
          (list 11 0.88173334 -0.15392319 0.00000000)
          (list 210 0.00000000 0.00000000 1.00000000)
         )
         (list
          (cons 0 "LINE")
          (cons 100 "AcDbEntity")
          (cons 67 0)
          (cons 8 "0")
          (cons 62 1)
          (cons 6 "Continuous")
          (cons 100 "AcDbLine")
          (list 10 0.90021294 -0.15306147 0.00000000)
          (list 11 0.88236088 -0.15395405 0.00000000)
          (list 210 0.00000000 0.00000000 1.00000000)
         )
         (list
          (cons 0 "LINE")
          (cons 100 "AcDbEntity")
          (cons 67 0)
          (cons 8 "0")
          (cons 62 1)
          (cons 6 "DASHED")
          (cons 100 "AcDbLine")
          (list 10 0.90026612 -0.15458470 0.00000000)
          (list 11 0.88272633 -0.15546169 0.00000000)
          (list 210 0.00000000 0.00000000 1.00000000)
         )
         (list (cons 0 "ENDBLK"))
        )
       )
       (T
        (progn
         (alert (strcat "!!! BLOCK DOES NOT EXIST - " BLKNAME " !!!"))
         nil
        )
       )
 )
)
