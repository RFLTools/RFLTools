;
;
;     Program written by Robert Livingston, 2016/06/22
;
;     WBLOCKLIST writes lisp code to create a selected block
;
;
(defun C:WBLOCKLIST (/ *error* CMDECHO ENT ENTLIST)
 (setq CMDECHO (getvar "CMDECHO"))
 (setvar "CMDECHO" 0)
 
 (defun *error* (msg)
  (if (/= nil OUTFILE) (close OUTFILE))
  (setvar "CMDECHO" CMDECHO)
  ;(setq *error* nil)
  (princ msg)
 )

 (if (/= nil (setq ENT (car (entsel "\nSelect block : "))))
  (if (= "INSERT" (cdr (assoc 0 (setq ENTLIST (entget ENT)))))
   (RFL:WBLOCKLIST (cdr (assoc 2 ENTLIST)))
   (princ "\n*** Entity not a block ***")
  )
 )

 (setvar "CMDECHO" CMDECHO)
)   
(defun RFL:WBLOCKLIST (BLOCKNAME / *error* CODE DIMZIN ENT ENTLIST NODE OUTFILE VAL)
 (setq DIMZIN (getvar "DIMZIN"))
 (setvar "DIMZIN" 0)
 
 (defun *error* (msg)
  (if (/= nil OUTFILE) (close OUTFILE))
  (setvar "DIMZIN" DIMZIN)
  ;(setq *error* nil)
  (princ msg)
 )

 (if (setq ENTLIST (tblsearch "BLOCK" BLOCKNAME))
  (progn
   (princ (strcat "\nFile written to: " (getenv "UserProfile") "\\Documents\\" (strcase (cdr (assoc 2 ENTLIST))) ".lsp\n"))
   (setq OUTFILE (open (strcat (getenv "UserProfile") "\\Documents\\" (strcase (cdr (assoc 2 ENTLIST))) ".lsp") "w"))
   (princ (strcat "       ((= (strcase BLKNAME) \"" (strcase (cdr (assoc 2 ENTLIST))) "\")\n") OUTFILE)
   (princ "        (list\n" OUTFILE)
   (princ "         (list\n" OUTFILE)
   (foreach NODE ENTLIST
    (setq CODE (car NODE))
    (cond ((and (= (type (cdr NODE)) 'STR) (/= CODE 5))
           (if (= CODE 7)
            (princ (strcat "          (cons " (itoa CODE) " \"" (getvar "TEXTSTYLE") "\")\n") OUTFILE)
            (princ (strcat "          (cons " (itoa CODE) " \"" (cdr NODE) "\")\n") OUTFILE)
           )
          )
          ((and (= (type (cdr NODE)) 'LIST) T)
           (progn
            (princ (strcat "          (list " (itoa CODE)) OUTFILE)
            (foreach VAL (cdr NODE)
             (princ (strcat " " (rtos VAL 2 8)) OUTFILE)
            )
            (princ ")\n" OUTFILE)
           )
          )
          ((and (= (type (cdr NODE)) 'INT) (>= CODE 0))
           (princ (strcat "          (cons " (itoa CODE) "  " (itoa (cdr NODE)) ")\n") OUTFILE)
          )
          ((and (= (type (cdr NODE)) 'REAL) T)
           (princ (strcat "          (cons " (itoa CODE) "  " (rtos (cdr NODE) 2 8) ")\n") OUTFILE)
          )
    )
   )
   (princ "         )\n" OUTFILE)
   (setq ENT (cdr (assoc -2 ENTLIST)))
   (while (/= nil ENT)
    (setq ENTLIST (entget ENT))
    (if (= "INSERT" (cdr (assoc 0 ENTLIST)))
     (RFL:WBLOCKLIST (cdr (assoc 2 ENTLIST)))
    )
    (princ "         (list\n" OUTFILE)
    (foreach NODE ENTLIST
     (setq CODE (car NODE))
     (cond ((and (= (type (cdr NODE)) 'STR) (/= CODE 5))
            (if (= CODE 7)
             (princ (strcat "          (cons " (itoa CODE) " \"" (getvar "TEXTSTYLE") "\")\n") OUTFILE)
             (princ (strcat "          (cons " (itoa CODE) " \"" (cdr NODE) "\")\n") OUTFILE)
            )
           )
           ((and (= (type (cdr NODE)) 'LIST) T)
            (progn
             (princ (strcat "          (list " (itoa CODE)) OUTFILE)
             (foreach VAL (cdr NODE)
              (princ (strcat " " (rtos VAL 2 8)) OUTFILE)
             )
             (princ ")\n" OUTFILE)
            )
           )
           ((and (= (type (cdr NODE)) 'INT) (>= CODE 0))
            (princ (strcat "          (cons " (itoa CODE) " " (itoa (cdr NODE)) ")\n") OUTFILE)
           )
           ((and (= (type (cdr NODE)) 'REAL) T)
            (princ (strcat "          (cons " (itoa CODE) "  " (rtos (cdr NODE) 2 8) ")\n") OUTFILE)
           )
     )
    )
    (princ "         )\n" OUTFILE)
    (setq ENT (entnext ENT))
   )
   (princ "         (list (cons 0 \"ENDBLK\"))\n" OUTFILE)
   (princ "        )\n" OUTFILE)
   (princ "       )\n" OUTFILE)
   (close OUTFILE)
  )
 )
 (setvar "DIMZIN" DIMZIN)
)
