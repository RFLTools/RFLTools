;
;
;     Program written by Robert Livingston, 02-10-21
;
;     MAKEENT is a utility for creating RFL blocks within lisp
;
;
;     Blocks included to date:
;                              ALTABLE01
;                              ALTABLE01DATA
;                              BCCURVETABLE
;                              BCCURVETABLEDATA
;                              CIRC
;                              CURVETABLE
;                              CURVETABLEDATA
;                              DRAWGRIDDEF
;                              FORCE
;                              POINT
;                              PR-CIRCLE
;                              PVI2
;                              RFLALIGN
;                              RFLPROF
;                              SLOPE
;                              SPOTELEVATION
;                              SPOTELEVATION2
;                              STALBL
;                              STATICK
;                              SUPER
;                              SURVEYSPOT
;
(defun C:MAKEENT (/ DCL_ID ACCEPTMAKEENT BLOCKINDEX BLOCKLIST CANCELMAKEENT UPDATEBLOCK)
 (defun ACCEPTMAKEENT (/ C)
  (RFL:MAKEENT (nth BLOCKINDEX BLOCKLIST))
  (setq BLOCKINDEX nil)
  (done_dialog)
  (unload_dialog DCL_ID)
 )
 (defun CANCELMAKEENT ()
  (setq BLOCKINDEX nil)
  (done_dialog)
  (unload_dialog DCL_ID)
 )

 (defun UPDATEBLOCK ()
  (setq BLOCKINDEX (atoi (get_tile "BLOCKNAME")))
  (done_dialog)
  (unload_dialog DCL_ID)
 )

 (setq BLOCKLIST (list "ALTABLE01"
                       "ALTABLE01DATA"
                       "BCCURVETABLE"
                       "BCCURVETABLEDATA"
                       "CIRC"
                       "CURVETABLE"
                       "CURVETABLEDATA"
                       "FORCE"
                       "POINT"
                       "PR-CIRCLE"
                       "PVI2"
                       "RFLALIGN"
                       "RFLPROF"
                       "SLOPE"
                       "SPOTELEVATION"
                       "SPOTELEVATION2"
                       "STALBL"
                       "STATICK"
                       "SUPER"
                       "SURVEYSPOT"
                 )
 )

 (setq BLOCKINDEX 0)

 (while (/= nil BLOCKINDEX)
  (if (= MAKEENTDCLNAME nil)
   (progn
    (setq MAKEENTDCLNAME (vl-filename-mktemp "rfl.dcl"))
    (MAKEDCL MAKEENTDCLNAME "MAKEENT")
   )
   (if (= nil (findfile MAKEENTDCLNAME))
    (progn
     (setq MAKEENTDCLNAME (vl-filename-mktemp "rfl.dcl"))
     (MAKEDCL MAKEENTDCLNAME "MAKEENT")
    )
   )
  )
  (setq DCL_ID (load_dialog MAKEENTDCLNAME))
  (if (not (new_dialog "MAKEENT" DCL_ID)) (exit))

  (start_list "BLOCKNAME")
  (mapcar 'add_list BLOCKLIST)
  (end_list)

  (set_tile "BLOCKNAME" (itoa BLOCKINDEX))

  (setq RFLALIGNSLBNAME "rflAlign.slb")
  (if (= nil (findfile RFLALIGNSLBNAME))
   (progn
    (setq RFLALIGNSLBNAME (vl-filename-mktemp "rfl.slb"))
    (MAKERFLSLB RFLALIGNSLBNAME)
   )
  )
  (start_image "IMAGE")
  (slide_image 0 0 (- (dimx_tile "IMAGE") 1)
                   (- (dimy_tile "IMAGE") 1)
                   (strcat RFLALIGNSLBNAME "(" (nth BLOCKINDEX BLOCKLIST) ")")
  )
  (end_image)

  (action_tile "BLOCKNAME" "(UPDATEBLOCK)")
  (action_tile "OK" "(ACCEPTMAKEENT)")
  (action_tile "CANCEL" "(CANCELMAKEENT)")

  (start_dialog)
 )
)
(defun RFL:MAKEENT (BLKNAME / BLOCKLIST NODE)
 (setq BLOCKLIST (RFL:GETBLOCKLIST BLKNAME))
 (if (/= nil BLOCKLIST)
  (progn
   (entmake)
   (foreach NODE BLOCKLIST
    (entmake NODE)
   )
  )
  nil
 )
)
(defun RFL:GETBLOCKLIST (BLKNAME)
 (cond
       ((= (strcase BLKNAME) "CURVETABLE")
        (list
         (list
          (cons 0 "BLOCK")
          (cons 2 "curvetable")
          (cons 70  2)
          (list 10 0.00000000 0.00000000 0.00000000)
         )
         (list
          (cons 0 "LINE")
          (cons 100 "AcDbEntity")
          (cons 67 0)
          (cons 8 "0")
          (cons 62 3)
          (cons 100 "AcDbLine")
          (list 10 0.00000000 0.00000000 0.00000000)
          (list 11 15.80000000 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 -58.49029637 0.00000000)
          (list 11 0.00000000 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 15.80000000 -58.49029637 0.00000000)
          (list 11 -0.00000001 -58.49029637 0.00000000)
          (list 210 0.00000000 0.00000000 1.00000000)
         )
         (list
          (cons 0 "TEXT")
          (cons 100 "AcDbEntity")
          (cons 67 0)
          (cons 8 "0")
          (cons 62 1)
          (cons 100 "AcDbText")
          (list 10 7.10473687 -52.43607287 0.00000000)
          (cons 40  2.00000000)
          (cons 1 "0")
          (cons 50  0.00000000)
          (cons 41  0.90000000)
          (cons 51  0.00000000)
          (cons 7 "Standard")
          (cons 71 0)
          (cons 72 4)
          (list 11 7.96187973 -51.43607287 0.00000000)
          (list 210 0.00000000 0.00000000 1.00000000)
          (cons 100 "AcDbText")
          (cons 73 0)
         )
         (list
          (cons 0 "LINE")
          (cons 100 "AcDbEntity")
          (cons 67 0)
          (cons 8 "0")
          (cons 62 1)
          (cons 100 "AcDbLine")
          (list 10 6.73510857 -51.43607287 0.00000000)
          (list 11 9.18865088 -51.43607287 0.00000000)
          (list 210 0.00000000 0.00000000 1.00000000)
         )
         (list
          (cons 0 "LINE")
          (cons 100 "AcDbEntity")
          (cons 67 0)
          (cons 8 "0")
          (cons 62 1)
          (cons 100 "AcDbLine")
          (list 10 6.73510857 -35.30000578 0.00000000)
          (list 11 9.18865088 -35.30000578 0.00000000)
          (list 210 0.00000000 0.00000000 1.00000000)
         )
         (list
          (cons 0 "TEXT")
          (cons 100 "AcDbEntity")
          (cons 67 0)
          (cons 8 "0")
          (cons 62 2)
          (cons 100 "AcDbText")
          (list 10 2.71616545 -5.06100582 0.00000000)
          (cons 40  2.40000000)
          (cons 1 "CURVE")
          (cons 50  0.00000000)
          (cons 41  0.90000000)
          (cons 51  0.00000000)
          (cons 7 "Standard")
          (cons 71 0)
          (cons 72 4)
          (list 11 7.96187974 -3.86100582 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 7.10473687 -36.30000578 0.00000000)
          (cons 40  2.00000000)
          (cons 1 "0")
          (cons 50  0.00000000)
          (cons 41  0.90000000)
          (cons 51  0.00000000)
          (cons 7 "Standard")
          (cons 71 0)
          (cons 72 4)
          (list 11 7.96187973 -35.30000578 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 6.59045117 -24.09649276 0.00000000)
          (cons 40  2.00000000)
          (cons 1 "Tc")
          (cons 50  0.00000000)
          (cons 41  0.90000000)
          (cons 51  0.00000000)
          (cons 7 "Standard")
          (cons 71 0)
          (cons 72 4)
          (list 11 7.96187974 -23.09649276 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 7.01902260 -16.09649277 0.00000000)
          (cons 40  2.00000000)
          (cons 1 "R")
          (cons 50  0.00000000)
          (cons 41  0.90000000)
          (cons 51  0.00000000)
          (cons 7 "Standard")
          (cons 71 0)
          (cons 72 4)
          (list 11 7.96187974 -15.09649277 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 6.46187973 -56.43607287 0.00000000)
          (cons 40  2.00000000)
          (cons 1 "Ls")
          (cons 50  0.00000000)
          (cons 41  0.90000000)
          (cons 51  0.00000000)
          (cons 7 "Standard")
          (cons 71 0)
          (cons 72 4)
          (list 11 7.96187973 -55.43607287 0.00000000)
          (list 210 0.00000000 0.00000000 1.00000000)
          (cons 100 "AcDbText")
          (cons 73 0)
         )
         (list
          (cons 0 "LWPOLYLINE")
          (cons 100 "AcDbEntity")
          (cons 67 0)
          (cons 8 "0")
          (cons 62 1)
          (cons 100 "AcDbPolyline")
          (cons 90 3)
          (cons 70 129)
          (cons 43  0.00000000)
          (cons 38  0.00000000)
          (cons 39  0.00000000)
          (list 10 7.56274961 -10.31684399)
          (cons 40  0.00000000)
          (cons 41  0.00000000)
          (cons 42  0.00000000)
          (cons 91 0)
          (list 10 6.76395409 -12.10003338)
          (cons 40  0.00000000)
          (cons 41  0.00000000)
          (cons 42  0.00000000)
          (cons 91 0)
          (list 10 8.36154514 -12.10003338)
          (cons 40  0.00000000)
          (cons 41  0.00000000)
          (cons 42  0.00000000)
          (cons 91 0)
          (list 210 0.00000000 0.00000000 1.00000000)
         )
         (list
          (cons 0 "TEXT")
          (cons 100 "AcDbEntity")
          (cons 67 0)
          (cons 8 "0")
          (cons 62 1)
          (cons 100 "AcDbText")
          (list 10 6.46187973 -40.30000578 0.00000000)
          (cons 40  2.00000000)
          (cons 1 "Ls")
          (cons 50  0.00000000)
          (cons 41  0.90000000)
          (cons 51  0.00000000)
          (cons 7 "Standard")
          (cons 71 0)
          (cons 72 4)
          (list 11 7.96187973 -39.30000578 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 6.41902260 -20.09649276 0.00000000)
          (cons 40  2.00000000)
          (cons 1 "Lc")
          (cons 50  0.00000000)
          (cons 41  0.90000000)
          (cons 51  0.00000000)
          (cons 7 "Standard")
          (cons 71 0)
          (cons 72 4)
          (list 11 7.96187974 -19.09649276 0.00000000)
          (list 210 0.00000000 0.00000000 1.00000000)
          (cons 100 "AcDbText")
          (cons 73 0)
         )
         (list
          (cons 0 "TEXT")
          (cons 100 "AcDbEntity")
          (cons 67 0)
          (cons 8 "0")
          (cons 62 1)
          (cons 100 "AcDbText")
          (list 10 8.36683460 -12.12014532 0.00000000)
          (cons 40  2.00000000)
          (cons 1 "c")
          (cons 50  0.00000000)
          (cons 41  0.90000000)
          (cons 51  0.00000000)
          (cons 7 "Standard")
          (cons 71 0)
          (cons 72 4)
          (list 11 9.13826317 -11.45347865 0.00000000)
          (list 210 0.00000000 0.00000000 1.00000000)
          (cons 100 "AcDbText")
          (cons 73 0)
         )
         (list
          (cons 0 "ATTDEF")
          (cons 100 "AcDbEntity")
          (cons 67 0)
          (cons 8 "0")
          (cons 62 2)
          (cons 100 "AcDbText")
          (list 10 -3.09714286 -57.69029637 0.00000000)
          (cons 40  0.80000000)
          (cons 1 "15.8")
          (cons 50  0.00000000)
          (cons 41  0.90000000)
          (cons 51  0.00000000)
          (cons 7 "Standard")
          (cons 71 0)
          (cons 72 2)
          (list 11 -0.80000000 -57.69029637 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 1)
          (cons 100 "AcDbLine")
          (list 10 15.91670335 -48.54374872 0.00000000)
          (list 11 0.11670335 -48.54374872 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.79999999 -42.35422927 0.00000000)
          (list 11 -0.00000001 -42.35422928 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.91670335 -32.40768164 0.00000000)
          (list 11 0.11670335 -32.40768164 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.91670335 -26.21816219 0.00000000)
          (list 11 0.11670335 -26.21816219 0.00000000)
          (list 210 0.00000000 0.00000000 1.00000000)
         )
         (list
          (cons 0 "LINE")
          (cons 100 "AcDbEntity")
          (cons 67 0)
          (cons 8 "0")
          (cons 62 1)
          (cons 100 "AcDbLine")
          (list 10 15.80000000 -7.72201164 0.00000000)
          (list 11 0.00000000 -7.72201164 0.00000000)
          (list 210 0.00000000 0.00000000 1.00000000)
         )
         (list (cons 0 "ENDBLK"))
        )
       )
       ((= (strcase BLKNAME) "CURVETABLEDATA")
        (list
         (list
          (cons 0 "BLOCK")
          (cons 2 "curvetableDATA")
          (cons 70  2)
          (list 10 0.00000000 0.00000000 0.00000000)
         )
         (list
          (cons 0 "ATTDEF")
          (cons 100 "AcDbEntity")
          (cons 67 0)
          (cons 8 "0")
          (cons 62 2)
          (cons 100 "AcDbText")
          (list 10 11.90000000 -3.86100582 0.00000000)
          (cons 40  2.40000000)
          (cons 1 "")
          (cons 50  0.00000000)
          (cons 41  0.90000000)
          (cons 51  0.00000000)
          (cons 7 "Standard")
          (cons 71 0)
          (cons 72 4)
          (list 11 11.90000000 -3.86100582 0.00000000)
          (list 210 0.00000000 0.00000000 1.00000000)
          (cons 100 "AcDbAttributeDefinition")
          (cons 280 0)
          (cons 3 "Curve Label")
          (cons 2 "LABEL")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -11.09649276 0.00000000)
          (cons 40  2.00000000)
          (cons 1 "")
          (cons 50  0.00000000)
          (cons 41  0.90000000)
          (cons 51  0.00000000)
          (cons 7 "Standard")
          (cons 71 0)
          (cons 72 4)
          (list 11 11.90000000 -11.09649276 0.00000000)
          (list 210 0.00000000 0.00000000 1.00000000)
          (cons 100 "AcDbAttributeDefinition")
          (cons 280 0)
          (cons 3 "Curve Delta")
          (cons 2 "CDELTA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -15.09649276 0.00000000)
          (cons 40  2.00000000)
          (cons 1 "")
          (cons 50  0.00000000)
          (cons 41  0.90000000)
          (cons 51  0.00000000)
          (cons 7 "Standard")
          (cons 71 0)
          (cons 72 4)
          (list 11 11.90000000 -15.09649276 0.00000000)
          (list 210 0.00000000 0.00000000 1.00000000)
          (cons 100 "AcDbAttributeDefinition")
          (cons 280 0)
          (cons 3 "Curve Radius")
          (cons 2 "CRADIUS")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -19.09649276 0.00000000)
          (cons 40  2.00000000)
          (cons 1 "")
          (cons 50  0.00000000)
          (cons 41  0.90000000)
          (cons 51  0.00000000)
          (cons 7 "Standard")
          (cons 71 0)
          (cons 72 4)
          (list 11 11.90000000 -19.09649276 0.00000000)
          (list 210 0.00000000 0.00000000 1.00000000)
          (cons 100 "AcDbAttributeDefinition")
          (cons 280 0)
          (cons 3 "Curve Length")
          (cons 2 "CLENGTH")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.90000000 -23.09649275 0.00000000)
          (cons 40  2.00000000)
          (cons 1 "")
          (cons 50  0.00000000)
          (cons 41  0.90000000)
          (cons 51  0.00000000)
          (cons 7 "Standard")
          (cons 71 0)
          (cons 72 4)
          (list 11 11.90000000 -23.09649275 0.00000000)
          (list 210 0.00000000 0.00000000 1.00000000)
          (cons 100 "AcDbAttributeDefinition")
          (cons 280 0)
          (cons 3 "Curve Tangent")
          (cons 2 "CTANGENT")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 11.89999999 -29.39285760 0.00000000)
          (cons 40  2.40000000)
          (cons 1 "")
          (cons 50  0.00000000)
          (cons 41  0.90000000)
          (cons 51  0.00000000)
          (cons 7 "Standard")
          (cons 71 0)
          (cons 72 4)
          (list 11 11.89999999 -29.39285760 0.00000000)
          (list 210 0.00000000 0.00000000 1.00000000)
          (cons 100 "AcDbAttributeDefinition")
          (cons 280 0)
          (cons 3 "Spiral Back Label")
          (cons 2 "SB")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -35.30000578 0.00000000)
          (cons 40  2.00000000)
          (cons 1 "")
          (cons 50  0.00000000)
          (cons 41  0.90000000)
          (cons 51  0.00000000)
          (cons 7 "Standard")
          (cons 71 0)
          (cons 72 4)
          (list 11 11.89999999 -35.30000578 0.00000000)
          (list 210 0.00000000 0.00000000 1.00000000)
          (cons 100 "AcDbAttributeDefinition")
          (cons 280 0)
          (cons 3 "Spiral Back Theta")
          (cons 2 "SBTHETA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -39.30000577 0.00000000)
          (cons 40  2.00000000)
          (cons 1 "")
          (cons 50  0.00000000)
          (cons 41  0.90000000)
          (cons 51  0.00000000)
          (cons 7 "Standard")
          (cons 71 0)
          (cons 72 4)
          (list 11 11.89999999 -39.30000577 0.00000000)
          (list 210 0.00000000 0.00000000 1.00000000)
          (cons 100 "AcDbAttributeDefinition")
          (cons 280 0)
          (cons 3 "Spiral Back Length")
          (cons 2 "SBLENGTH")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 11.89999999 -45.52892469 0.00000000)
          (cons 40  2.40000000)
          (cons 1 "")
          (cons 50  0.00000000)
          (cons 41  0.90000000)
          (cons 51  0.00000000)
          (cons 7 "Standard")
          (cons 71 0)
          (cons 72 4)
          (list 11 11.89999999 -45.52892469 0.00000000)
          (list 210 0.00000000 0.00000000 1.00000000)
          (cons 100 "AcDbAttributeDefinition")
          (cons 280 0)
          (cons 3 "Spiral Ahead Label")
          (cons 2 "SA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -51.43607287 0.00000000)
          (cons 40  2.00000000)
          (cons 1 "")
          (cons 50  0.00000000)
          (cons 41  0.90000000)
          (cons 51  0.00000000)
          (cons 7 "Standard")
          (cons 71 0)
          (cons 72 4)
          (list 11 11.89999999 -51.43607287 0.00000000)
          (list 210 0.00000000 0.00000000 1.00000000)
          (cons 100 "AcDbAttributeDefinition")
          (cons 280 0)
          (cons 3 "Spiral Ahead Theta")
          (cons 2 "SATHETA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 11.89999999 -55.43607286 0.00000000)
          (cons 40  2.00000000)
          (cons 1 "")
          (cons 50  0.00000000)
          (cons 41  0.90000000)
          (cons 51  0.00000000)
          (cons 7 "Standard")
          (cons 71 0)
          (cons 72 4)
          (list 11 11.89999999 -55.43607286 0.00000000)
          (list 210 0.00000000 0.00000000 1.00000000)
          (cons 100 "AcDbAttributeDefinition")
          (cons 280 0)
          (cons 3 "Spiral Ahead Length")
          (cons 2 "SALENGTH")
          (cons 70 0)
          (cons 73 0)
          (cons 74 0)
          (cons 280 0)
         )
         (list
          (cons 0 "LINE")
          (cons 100 "AcDbEntity")
          (cons 67 0)
          (cons 8 "0")
          (cons 62 1)
          (cons 100 "AcDbLine")
          (list 10 0.00000000 -32.40768166 0.00000000)
          (list 11 23.80000000 -32.40768168 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -26.21816219 0.00000000)
          (list 11 23.80000000 -26.21816218 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -7.72201164 0.00000000)
          (list 11 23.80000000 -7.72201163 0.00000000)
          (list 210 0.00000000 0.00000000 1.00000000)
         )
         (list
          (cons 0 "LINE")
          (cons 100 "AcDbEntity")
          (cons 67 0)
          (cons 8 "0")
          (cons 62 1)
          (cons 100 "AcDbLine")
          (list 10 23.80000000 -42.35422928 0.00000000)
          (list 11 0.00000000 -42.35422928 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -48.54374875 0.00000000)
          (list 11 23.80000000 -48.54374876 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -58.49029637 0.00000000)
          (list 11 0.00000000 0.00000000 0.00000000)
          (list 210 0.00000000 0.00000000 1.00000000)
         )
         (list
          (cons 0 "ATTDEF")
          (cons 100 "AcDbEntity")
          (cons 67 0)
          (cons 8 "0")
          (cons 62 2)
          (cons 100 "AcDbText")
          (list 10 -3.09714286 -57.69029637 0.00000000)
          (cons 40  0.80000000)
          (cons 1 "23.8")
          (cons 50  0.00000000)
          (cons 41  0.90000000)
          (cons 51  0.00000000)
          (cons 7 "Standard")
          (cons 71 0)
          (cons 72 2)
          (list 11 -0.80000000 -57.69029637 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 3)
          (cons 100 "AcDbLine")
          (list 10 0.00000000 -58.49029637 0.00000000)
          (list 11 23.80000000 -58.49029639 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 0.00000000 0.00000000)
          (list 11 23.80000000 0.00000001 0.00000000)
          (list 210 0.00000000 0.00000000 1.00000000)
         )
         (list (cons 0 "ENDBLK"))
        )
       )
       ((= (strcase BLKNAME) "BCCURVETABLEDATA")
        (list
         (list
          (cons 0 "BLOCK")
          (cons 2 "BCCurveTableData")
          (cons 70  2)
          (list 10 0.00000000 0.00000000 0.00000000)
         )
         (list
          (cons 0 "LINE")
          (cons 100 "AcDbEntity")
          (cons 67 0)
          (cons 8 "0")
          (cons 62 3)
          (cons 100 "AcDbLine")
          (list 10 20.00000000 0.00000000 0.00000000)
          (list 11 0.00000000 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 -45.32799986 0.00000000)
          (list 11 20.00000000 -45.32799944 0.00000000)
          (list 210 0.00000000 0.00000000 1.00000000)
         )
         (list
          (cons 0 "LINE")
          (cons 100 "AcDbEntity")
          (cons 67 0)
          (cons 8 "0")
          (cons 62 3)
          (cons 100 "AcDbLine")
          (list 10 20.00000000 -2.83300000 0.00000000)
          (list 11 0.00000000 -2.83300000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -5.66600000 0.00000000)
          (list 11 0.00000000 -5.66600000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -8.49900000 0.00000000)
          (list 11 0.00000000 -8.49900000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -11.33200000 0.00000000)
          (list 11 0.00000000 -11.33200000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -14.16500000 0.00000000)
          (list 11 0.00000000 -14.16500000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -16.99800000 0.00000000)
          (list 11 0.00000000 -16.99800000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -19.83100000 0.00000000)
          (list 11 0.00000000 -19.83100000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -28.33000000 0.00000000)
          (list 11 0.00000000 -28.33000000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -31.16300000 0.00000000)
          (list 11 0.00000000 -31.16300000 0.00000000)
          (list 210 0.00000000 0.00000000 1.00000000)
         )
         (list
          (cons 0 "LINE")
          (cons 100 "AcDbEntity")
          (cons 67 0)
          (cons 8 "0")
          (cons 62 3)
          (cons 100 "AcDbLine")
          (list 10 20.00000000 -36.82900000 0.00000000)
          (list 11 0.00000000 -36.82900000 0.00000000)
          (list 210 0.00000000 0.00000000 1.00000000)
         )
         (list
          (cons 0 "LINE")
          (cons 100 "AcDbEntity")
          (cons 67 0)
          (cons 8 "0")
          (cons 62 3)
          (cons 100 "AcDbLine")
          (list 10 20.00000000 -39.66200000 0.00000000)
          (list 11 0.00000000 -39.66200000 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 0.00000000 0.00000000)
          (list 11 0.00000000 -45.32800000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -22.66400000 0.00000000)
          (list 11 0.00000000 -22.66400000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -25.49700000 0.00000000)
          (list 11 0.00000000 -25.49700000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -33.99600000 0.00000000)
          (list 11 0.00000000 -33.99600000 0.00000000)
          (list 210 0.00000000 0.00000000 1.00000000)
         )
         (list
          (cons 0 "LINE")
          (cons 100 "AcDbEntity")
          (cons 67 0)
          (cons 8 "0")
          (cons 62 30)
          (cons 100 "AcDbLine")
          (list 10 20.00000000 -42.49500000 0.00000000)
          (list 11 0.00000000 -42.49500000 0.00000000)
          (list 210 0.00000000 0.00000000 1.00000000)
         )
         (list
          (cons 0 "ATTDEF")
          (cons 100 "AcDbEntity")
          (cons 67 0)
          (cons 8 "0")
          (cons 100 "AcDbText")
          (list 10 1.83394390 -2.30830557 0.00000000)
          (cons 40  1.72500000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Number")
          (cons 2 "LABEL")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -4.87449879 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Radius")
          (cons 2 "CRADIUS")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -7.70783213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Total Delta")
          (cons 2 "DELTA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -10.54083213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Delta")
          (cons 2 "CDELTA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -13.37449879 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Tangent In")
          (cons 2 "CTANGENT1")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -16.20749879 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Tangent Out")
          (cons 2 "CTANGENT2")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -19.04083213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Curve Length")
          (cons 2 "CLENGTH")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -21.87383213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "External Distance (Es or Ec)")
          (cons 2 "EXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -24.70683213 0.00000000)
          (cons 40  1.25000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Superelevation")
          (cons 2 "E")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -27.53983213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Length In")
          (cons 2 "LS1")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -30.37283213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Theta In")
          (cons 2 "THETA1")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -33.20583213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Length Out")
          (cons 2 "LS2")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -36.03883213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Spiral Theta Out")
          (cons 2 "THETA2")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -38.87183213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "PI Station")
          (cons 2 "PISTA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -41.70483213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "PI Northing")
          (cons 2 "PINORTHING")
          (cons 70 0)
          (cons 73 0)
          (cons 74 0)
          (cons 280 0)
         )
         (list
          (cons 0 "ATTDEF")
          (cons 100 "AcDbEntity")
          (cons 67 0)
          (cons 8 "0")
          (cons 100 "AcDbText")
          (list 10 4.00000000 -44.53783213 0.00000000)
          (cons 40  1.25000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "PI EASTING")
          (cons 2 "PIEASTING")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 -3.35238094 -44.52799986 0.00000000)
          (cons 40  0.80000000)
          (cons 1 "20.0")
          (cons 50  0.00000000)
          (cons 41  1.00000000)
          (cons 51  0.00000000)
          (cons 7 "Standard")
          (cons 71 0)
          (cons 72 2)
          (list 11 -0.79999999 -44.52799986 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list (cons 0 "ENDBLK"))
        )
       )
       ((= (strcase BLKNAME) "CIRC")
        (list
         (list
          (cons 0 "BLOCK")
          (cons 2 "CIRC")
          (cons 70  0)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  5.00000000)
          (list 210 0.00000000 0.00000000 1.00000000)
         )
         (list (cons 0 "ENDBLK"))
        )
       )
       ((= (strcase BLKNAME) "ALTABLE01DATA")
        (list
         (list
          (cons 0 "BLOCK")
          (cons 2 "altable01data")
          (cons 70  2)
          (list 10 0.00000000 0.00000000 0.00000000)
         )
         (list
          (cons 0 "ATTDEF")
          (cons 100 "AcDbEntity")
          (cons 67 0)
          (cons 8 "0")
          (cons 62 1)
          (cons 100 "AcDbText")
          (list 10 9.74777432 -3.00000000 0.00000000)
          (cons 40  2.50000000)
          (cons 1 "")
          (cons 50  0.00000000)
          (cons 41  0.90000000)
          (cons 51  0.00000000)
          (cons 7 "Standard")
          (cons 71 0)
          (cons 72 4)
          (list 11 9.74777432 -3.00000000 0.00000000)
          (list 210 0.00000000 0.00000000 1.00000000)
          (cons 100 "AcDbAttributeDefinition")
          (cons 280 0)
          (cons 3 "Point Number")
          (cons 2 "PNT")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 34.45844733 -3.00000000 0.00000000)
          (cons 40  2.50000000)
          (cons 1 "")
          (cons 50  0.00000000)
          (cons 41  0.90000000)
          (cons 51  0.00000000)
          (cons 7 "Standard")
          (cons 71 0)
          (cons 72 4)
          (list 11 34.45844733 -3.00000000 0.00000000)
          (list 210 0.00000000 0.00000000 1.00000000)
          (cons 100 "AcDbAttributeDefinition")
          (cons 280 0)
          (cons 3 "Station")
          (cons 2 "STA")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 64.22270621 -3.00000000 0.00000000)
          (cons 40  2.50000000)
          (cons 1 "")
          (cons 50  0.00000000)
          (cons 41  0.90000000)
          (cons 51  0.00000000)
          (cons 7 "Standard")
          (cons 71 0)
          (cons 72 4)
          (list 11 64.22270621 -3.00000000 0.00000000)
          (list 210 0.00000000 0.00000000 1.00000000)
          (cons 100 "AcDbAttributeDefinition")
          (cons 280 0)
          (cons 3 "Northing")
          (cons 2 "NORTHING")
          (cons 70 0)
          (cons 73 0)
          (cons 74 0)
          (cons 280 0)
         )
         (list
          (cons 0 "ATTDEF")
          (cons 100 "AcDbEntity")
          (cons 67 0)
          (cons 8 "0")
          (cons 62 1)
          (cons 100 "AcDbText")
          (list 10 93.98696509 -3.00000000 0.00000000)
          (cons 40  2.50000000)
          (cons 1 "")
          (cons 50  0.00000000)
          (cons 41  0.90000000)
          (cons 51  0.00000000)
          (cons 7 "Standard")
          (cons 71 0)
          (cons 72 4)
          (list 11 93.98696509 -3.00000000 0.00000000)
          (list 210 0.00000000 0.00000000 1.00000000)
          (cons 100 "AcDbAttributeDefinition")
          (cons 280 0)
          (cons 3 "Easting")
          (cons 2 "EASTING")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 -3.01428571 -5.00000000 0.00000000)
          (cons 40  1.00000000)
          (cons 1 "6.0")
          (cons 50  0.00000000)
          (cons 41  0.90000000)
          (cons 51  0.00000000)
          (cons 7 "Standard")
          (cons 71 0)
          (cons 72 2)
          (list 11 -1.00000000 -5.00000000 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 3)
          (cons 100 "AcDbLine")
          (list 10 0.00000000 -6.00000000 0.00000000)
          (list 11 0.00000000 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 19.65708710 -6.00000000 0.00000000)
          (list 11 19.65708710 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 49.42134598 -6.00000000 0.00000000)
          (list 11 49.42134598 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 79.18560486 -6.00000000 0.00000000)
          (list 11 79.18560486 0.00000000 0.00000000)
          (list 210 0.00000000 0.00000000 1.00000000)
         )
         (list
          (cons 0 "LINE")
          (cons 100 "AcDbEntity")
          (cons 67 0)
          (cons 8 "0")
          (cons 62 3)
          (cons 100 "AcDbLine")
          (list 10 108.94986374 -6.00000000 0.00000000)
          (list 11 108.94986374 0.00000000 0.00000000)
          (list 210 0.00000000 0.00000000 1.00000000)
         )
         (list (cons 0 "ENDBLK"))
        )
       )
       ((= (strcase BLKNAME) "BCCURVETABLE")
        (list
         (list
          (cons 0 "BLOCK")
          (cons 2 "BCCurveTable")
          (cons 70  2)
          (list 10 0.00000000 0.00000000 0.00000000)
         )
         (list
          (cons 0 "LINE")
          (cons 100 "AcDbEntity")
          (cons 67 0)
          (cons 8 "0")
          (cons 62 30)
          (cons 100 "AcDbLine")
          (list 10 7.00000000 -33.99600000 0.00000000)
          (list 11 0.00000000 -33.99600000 0.00000000)
          (list 210 0.00000000 0.00000000 1.00000000)
         )
         (list
          (cons 0 "LWPOLYLINE")
          (cons 100 "AcDbEntity")
          (cons 67 0)
          (cons 8 "0")
          (cons 62 3)
          (cons 100 "AcDbPolyline")
          (cons 90 4)
          (cons 70 128)
          (cons 43  0.00000000)
          (cons 38  0.00000000)
          (cons 39  0.00000000)
          (list 10 7.00000000 0.00000000)
          (cons 40  0.00000000)
          (cons 41  0.00000000)
          (cons 42  0.00000000)
          (cons 91 0)
          (list 10 0.00000000 0.00000000)
          (cons 40  0.00000000)
          (cons 41  0.00000000)
          (cons 42  0.00000000)
          (cons 91 0)
          (list 10 0.00000000 -45.32800000)
          (cons 40  0.00000000)
          (cons 41  0.00000000)
          (cons 42  0.00000000)
          (cons 91 0)
          (list 10 7.00000000 -45.32799986)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 62 3)
          (cons 100 "AcDbLine")
          (list 10 7.00000000 -2.83300000 0.00000000)
          (list 11 0.00000000 -2.83300000 0.00000000)
          (list 210 0.00000000 0.00000000 1.00000000)
         )
         (list
          (cons 0 "LWPOLYLINE")
          (cons 100 "AcDbEntity")
          (cons 67 0)
          (cons 8 "0")
          (cons 100 "AcDbPolyline")
          (cons 90 3)
          (cons 70 1)
          (cons 43  0.00000000)
          (cons 38  0.00000000)
          (cons 39  0.00000000)
          (list 10 2.40507917 -9.29116667)
          (cons 40  0.00000000)
          (cons 41  0.00000000)
          (cons 42  0.00000000)
          (cons 91 0)
          (list 10 3.03007917 -10.54116667)
          (cons 40  0.00000000)
          (cons 41  0.00000000)
          (cons 42  0.00000000)
          (cons 91 0)
          (list 10 1.78007917 -10.54116667)
          (cons 40  0.00000000)
          (cons 41  0.00000000)
          (cons 42  0.00000000)
          (cons 91 0)
          (list 210 0.00000000 0.00000000 1.00000000)
         )
         (list
          (cons 0 "LWPOLYLINE")
          (cons 100 "AcDbEntity")
          (cons 67 0)
          (cons 8 "0")
          (cons 100 "AcDbPolyline")
          (cons 90 3)
          (cons 70 1)
          (cons 43  0.00000000)
          (cons 38  0.00000000)
          (cons 39  0.00000000)
          (list 10 2.40507917 -6.45783333)
          (cons 40  0.00000000)
          (cons 41  0.00000000)
          (cons 42  0.00000000)
          (cons 91 0)
          (list 10 3.03007917 -7.70783333)
          (cons 40  0.00000000)
          (cons 41  0.00000000)
          (cons 42  0.00000000)
          (cons 91 0)
          (list 10 1.78007917 -7.70783333)
          (cons 40  0.00000000)
          (cons 41  0.00000000)
          (cons 42  0.00000000)
          (cons 91 0)
          (list 210 0.00000000 0.00000000 1.00000000)
         )
         (list
          (cons 0 "LINE")
          (cons 100 "AcDbEntity")
          (cons 67 0)
          (cons 8 "0")
          (cons 62 30)
          (cons 100 "AcDbLine")
          (list 10 7.00000000 -5.66600000 0.00000000)
          (list 11 0.00000000 -5.66600000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -8.49900000 0.00000000)
          (list 11 0.00000000 -8.49900000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -11.33200000 0.00000000)
          (list 11 0.00000000 -11.33200000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -16.99800000 0.00000000)
          (list 11 0.00000000 -16.99800000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -19.83100000 0.00000000)
          (list 11 0.00000000 -19.83100000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -22.66400000 0.00000000)
          (list 11 0.00000000 -22.66400000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -31.16300000 0.00000000)
          (list 11 0.00000000 -31.16300000 0.00000000)
          (list 210 0.00000000 0.00000000 1.00000000)
         )
         (list
          (cons 0 "LINE")
          (cons 100 "AcDbEntity")
          (cons 67 0)
          (cons 8 "0")
          (cons 62 3)
          (cons 100 "AcDbLine")
          (list 10 7.00000000 -36.82900000 0.00000000)
          (list 11 0.00000000 -36.82900000 0.00000000)
          (list 210 0.00000000 0.00000000 1.00000000)
         )
         (list
          (cons 0 "TEXT")
          (cons 100 "AcDbEntity")
          (cons 67 0)
          (cons 8 "0")
          (cons 100 "AcDbText")
          (list 10 2.83169909 -10.54155327 0.00000000)
          (cons 40  1.25000000)
          (cons 1 " c")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "LINE")
          (cons 100 "AcDbEntity")
          (cons 67 0)
          (cons 8 "0")
          (cons 62 3)
          (cons 100 "AcDbLine")
          (list 10 7.00000000 -39.66200000 0.00000000)
          (list 11 0.00000000 -39.66200000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -42.49500000 0.00000000)
          (list 11 0.00000000 -42.49500000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -25.49700000 0.00000000)
          (list 11 0.00000000 -25.49700000 0.00000000)
          (list 210 0.00000000 0.00000000 1.00000000)
         )
         (list
          (cons 0 "LINE")
          (cons 100 "AcDbEntity")
          (cons 67 0)
          (cons 8 "0")
          (cons 62 30)
          (cons 100 "AcDbLine")
          (list 10 7.00000000 -28.33000000 0.00000000)
          (list 11 0.00000000 -28.33000000 0.00000000)
          (list 210 0.00000000 0.00000000 1.00000000)
         )
         (list
          (cons 0 "LINE")
          (cons 100 "AcDbEntity")
          (cons 67 0)
          (cons 8 "0")
          (cons 100 "AcDbLine")
          (list 10 1.96719380 -29.77114901 0.00000000)
          (list 11 2.79195186 -29.77114901 0.00000000)
          (list 210 0.00000000 0.00000000 1.00000000)
         )
         (list
          (cons 0 "LINE")
          (cons 100 "AcDbEntity")
          (cons 67 0)
          (cons 8 "0")
          (cons 100 "AcDbLine")
          (list 10 1.96719380 -35.43714901 0.00000000)
          (list 11 2.79195186 -35.43714901 0.00000000)
          (list 210 0.00000000 0.00000000 1.00000000)
         )
         (list
          (cons 0 "TEXT")
          (cons 100 "AcDbEntity")
          (cons 67 0)
          (cons 8 "0")
          (cons 100 "AcDbText")
          (list 10 1.78007918 -4.87450000 0.00000000)
          (cons 40  1.25000000)
          (cons 1 "R")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -24.70750000 0.00000000)
          (cons 40  1.25000000)
          (cons 1 "e")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -13.37450000 0.00000000)
          (cons 40  1.25000000)
          (cons 1 "A.D.1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -19.04083333 0.00000000)
          (cons 40  1.25000000)
          (cons 1 "ARC")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -21.87416667 0.00000000)
          (cons 40  1.25000000)
          (cons 1 "Ext")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -30.37416667 0.00000000)
          (cons 40  1.25000000)
          (cons 1 "0s1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -27.54083333 0.00000000)
          (cons 40  1.25000000)
          (cons 1 "Ls1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -33.20683333 0.00000000)
          (cons 40  1.25000000)
          (cons 1 "Ls2")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -36.04016667 0.00000000)
          (cons 40  1.25000000)
          (cons 1 "0s2")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -38.87350000 0.00000000)
          (cons 40  1.25000000)
          (cons 1 "PI")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -44.54016667 0.00000000)
          (cons 40  1.25000000)
          (cons 1 "E.")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 1.78007917 -41.70683333 0.00000000)
          (cons 40  1.25000000)
          (cons 1 "N.")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "LINE")
          (cons 100 "AcDbEntity")
          (cons 67 0)
          (cons 8 "0")
          (cons 62 30)
          (cons 100 "AcDbLine")
          (list 10 7.00000000 -14.16500000 0.00000000)
          (list 11 0.00000000 -14.16500000 0.00000000)
          (list 210 0.00000000 0.00000000 1.00000000)
         )
         (list
          (cons 0 "TEXT")
          (cons 100 "AcDbEntity")
          (cons 67 0)
          (cons 8 "0")
          (cons 100 "AcDbText")
          (list 10 1.78007917 -16.20750000 0.00000000)
          (cons 40  1.25000000)
          (cons 1 "A.D.2")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "ATTDEF")
          (cons 100 "AcDbEntity")
          (cons 67 0)
          (cons 8 "0")
          (cons 62 2)
          (cons 100 "AcDbText")
          (list 10 -2.59047618 -44.52800000 0.00000000)
          (cons 40  0.80000000)
          (cons 1 "7.0")
          (cons 50  0.00000000)
          (cons 41  1.00000000)
          (cons 51  0.00000000)
          (cons 7 "Standard")
          (cons 71 0)
          (cons 72 2)
          (list 11 -0.79999999 -44.52800000 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list (cons 0 "ENDBLK"))
        )
       )
       ((= (strcase BLKNAME) "ALTABLE01")
        (list
         (list
          (cons 0 "BLOCK")
          (cons 2 "ALTable01")
          (cons 70  2)
          (cons 4 "")
          (list 10 0.00000000 0.00000000 0.00000000)
         )
         (list
          (cons 0 "ATTDEF")
          (cons 100 "AcDbEntity")
          (cons 67 0)
          (cons 8 "0")
          (cons 62 2)
          (cons 100 "AcDbText")
          (list 10 54.29019558 -4.83819420 0.00000000)
          (cons 40  3.00000000)
          (cons 1 "")
          (cons 50  0.00000000)
          (cons 41  0.90000000)
          (cons 51  0.00000000)
          (cons 7 "Standard")
          (cons 71 0)
          (cons 72 4)
          (list 11 54.29019558 -4.83819420 0.00000000)
          (list 210 0.00000000 0.00000000 1.00000000)
          (cons 100 "AcDbAttributeDefinition")
          (cons 280 0)
          (cons 3 "Title")
          (cons 2 "TITLE")
          (cons 70 0)
          (cons 73 0)
          (cons 74 0)
          (cons 280 0)
         )
         (list
          (cons 0 "ATTDEF")
          (cons 100 "AcDbEntity")
          (cons 67 0)
          (cons 8 "0")
          (cons 62 2)
          (cons 100 "AcDbText")
          (list 10 -3.91428571 -22.40000000 0.00000000)
          (cons 40  1.00000000)
          (cons 1 "23.4")
          (cons 50  0.00000000)
          (cons 41  0.90000000)
          (cons 51  0.00000000)
          (cons 7 "Standard")
          (cons 71 0)
          (cons 72 2)
          (list 11 -1.00000000 -22.40000000 0.00000000)
          (list 210 0.00000000 0.00000000 1.00000000)
          (cons 100 "AcDbAttributeDefinition")
          (cons 280 0)
          (cons 3 "STEP")
          (cons 2 "STEP")
          (cons 70 9)
          (cons 73 0)
          (cons 74 0)
          (cons 280 0)
         )
         (list
          (cons 0 "LINE")
          (cons 100 "AcDbEntity")
          (cons 67 0)
          (cons 8 "0")
          (cons 62 3)
          (cons 100 "AcDbLine")
          (list 10 0.00000000 -9.66445149 0.00000000)
          (list 11 108.94986374 -9.66445148 0.00000000)
          (list 210 0.00000000 0.00000000 1.00000000)
         )
         (list
          (cons 0 "LINE")
          (cons 100 "AcDbEntity")
          (cons 67 0)
          (cons 8 "0")
          (cons 62 1)
          (cons 100 "AcDbLine")
          (list 10 0.00000000 -23.40000000 0.00000000)
          (list 11 108.94986374 -23.39999997 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 0.00000000 0.00000000)
          (list 11 108.94986374 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 19.65708710 -23.39999999 0.00000000)
          (list 11 19.65708710 -9.66445148 0.00000000)
          (list 210 0.00000000 0.00000000 1.00000000)
         )
         (list
          (cons 0 "LINE")
          (cons 100 "AcDbEntity")
          (cons 67 0)
          (cons 8 "0")
          (cons 62 3)
          (cons 100 "AcDbLine")
          (list 10 0.00000000 -23.40000000 0.00000000)
          (list 11 0.00000000 0.00000000 0.00000000)
          (list 210 0.00000000 0.00000000 1.00000000)
         )
         (list
          (cons 0 "TEXT")
          (cons 100 "AcDbEntity")
          (cons 67 0)
          (cons 8 "0")
          (cons 62 2)
          (cons 100 "AcDbText")
          (list 10 26.76456700 -14.77855408 0.00000000)
          (cons 40  3.00000000)
          (cons 1 "STATION")
          (cons 50  0.00000000)
          (cons 41  0.90000000)
          (cons 51  0.00000000)
          (cons 7 "Standard")
          (cons 71 0)
          (cons 72 4)
          (list 11 34.54313843 -13.27855408 0.00000000)
          (list 210 0.00000000 0.00000000 1.00000000)
          (cons 100 "AcDbText")
          (cons 73 0)
         )
         (list
          (cons 0 "LINE")
          (cons 100 "AcDbEntity")
          (cons 67 0)
          (cons 8 "0")
          (cons 62 3)
          (cons 100 "AcDbLine")
          (list 10 108.94986374 -23.39999997 0.00000000)
          (list 11 108.94986374 0.00000000 0.00000000)
          (list 210 0.00000000 0.00000000 1.00000000)
         )
         (list
          (cons 0 "LINE")
          (cons 100 "AcDbEntity")
          (cons 67 0)
          (cons 8 "0")
          (cons 62 1)
          (cons 100 "AcDbLine")
          (list 10 49.42134598 -23.39999999 0.00000000)
          (list 11 49.42134598 -9.66445148 0.00000000)
          (list 210 0.00000000 0.00000000 1.00000000)
         )
         (list
          (cons 0 "LINE")
          (cons 100 "AcDbEntity")
          (cons 67 0)
          (cons 8 "0")
          (cons 62 1)
          (cons 100 "AcDbLine")
          (list 10 49.42134598 -16.63964179 0.00000000)
          (list 11 108.94986374 -16.63964178 0.00000000)
          (list 210 0.00000000 0.00000000 1.00000000)
         )
         (list
          (cons 0 "TEXT")
          (cons 100 "AcDbEntity")
          (cons 67 0)
          (cons 8 "0")
          (cons 62 2)
          (cons 100 "AcDbText")
          (list 10 57.68204685 -21.65607812 0.00000000)
          (cons 40  3.00000000)
          (cons 1 "NORTH")
          (cons 50  0.00000000)
          (cons 41  0.90000000)
          (cons 51  0.00000000)
          (cons 7 "Standard")
          (cons 71 0)
          (cons 72 4)
          (list 11 64.30347542 -20.15607812 0.00000000)
          (list 210 0.00000000 0.00000000 1.00000000)
          (cons 100 "AcDbText")
          (cons 73 0)
         )
         (list
          (cons 0 "LINE")
          (cons 100 "AcDbEntity")
          (cons 67 0)
          (cons 8 "0")
          (cons 62 1)
          (cons 100 "AcDbLine")
          (list 10 79.18560486 -23.39999998 0.00000000)
          (list 11 79.18560486 -16.63964178 0.00000000)
          (list 210 0.00000000 0.00000000 1.00000000)
         )
         (list
          (cons 0 "TEXT")
          (cons 100 "AcDbEntity")
          (cons 67 0)
          (cons 8 "0")
          (cons 62 2)
          (cons 100 "AcDbText")
          (list 10 89.18202001 -21.65607812 0.00000000)
          (cons 40  3.00000000)
          (cons 1 "EAST")
          (cons 50  0.00000000)
          (cons 41  0.90000000)
          (cons 51  0.00000000)
          (cons 7 "Standard")
          (cons 71 0)
          (cons 72 4)
          (list 11 94.06773430 -20.15607812 0.00000000)
          (list 210 0.00000000 0.00000000 1.00000000)
          (cons 100 "AcDbText")
          (cons 73 0)
         )
         (list
          (cons 0 "TEXT")
          (cons 100 "AcDbEntity")
          (cons 67 0)
          (cons 8 "0")
          (cons 62 2)
          (cons 100 "AcDbText")
          (list 10 65.68560485 -14.77855408 0.00000000)
          (cons 40  3.00000000)
          (cons 1 "COORDINATES")
          (cons 50  0.00000000)
          (cons 41  0.90000000)
          (cons 51  0.00000000)
          (cons 7 "Standard")
          (cons 71 0)
          (cons 72 4)
          (list 11 79.18560485 -13.27855408 0.00000000)
          (list 210 0.00000000 0.00000000 1.00000000)
          (cons 100 "AcDbText")
          (cons 73 0)
         )
         (list (cons 0 "ENDBLK"))
        )
       )
       ((= (strcase BLKNAME) "SURVEYSPOT")
        (list
         (list
          (cons 0 "BLOCK")
          (cons 2 "surveyspot")
          (cons 70  2)
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 1.00000000 1.21428571 0.00000000)
          (cons 40  1.00000000)
          (cons 1 "")
          (cons 50  0.00000000)
          (cons 41  0.75000000)
          (cons 51  0.00000000)
          (cons 7 "Standard")
          (cons 71 0)
          (cons 72 0)
          (list 11 1.00000000 1.71428571 0.00000000)
          (list 210 0.00000000 0.00000000 1.00000000)
          (cons 100 "AcDbAttributeDefinition")
          (cons 280 0)
          (cons 3 "Point Number")
          (cons 2 "PNTNO")
          (cons 70 0)
          (cons 73 0)
          (cons 74 2)
          (cons 280 0)
         )
         (list
          (cons 0 "ATTDEF")
          (cons 100 "AcDbEntity")
          (cons 67 0)
          (cons 8 "0")
          (cons 100 "AcDbText")
          (list 10 1.00000000 -0.50000000 0.00000000)
          (cons 40  1.00000000)
          (cons 1 "")
          (cons 50  0.00000000)
          (cons 41  0.75000000)
          (cons 51  0.00000000)
          (cons 7 "Standard")
          (cons 71 0)
          (cons 72 0)
          (list 11 1.00000000 0.00000000 0.00000000)
          (list 210 0.00000000 0.00000000 1.00000000)
          (cons 100 "AcDbAttributeDefinition")
          (cons 280 0)
          (cons 3 "ELEVATION")
          (cons 2 "ELEV")
          (cons 70 0)
          (cons 73 0)
          (cons 74 2)
          (cons 280 0)
         )
         (list
          (cons 0 "ATTDEF")
          (cons 100 "AcDbEntity")
          (cons 67 0)
          (cons 8 "0")
          (cons 100 "AcDbText")
          (list 10 1.00000000 -2.21428571 0.00000000)
          (cons 40  1.00000000)
          (cons 1 "")
          (cons 50  0.00000000)
          (cons 41  0.75000000)
          (cons 51  0.00000000)
          (cons 7 "Standard")
          (cons 71 0)
          (cons 72 0)
          (list 11 1.00000000 -1.71428571 0.00000000)
          (list 210 0.00000000 0.00000000 1.00000000)
          (cons 100 "AcDbAttributeDefinition")
          (cons 280 0)
          (cons 3 "Description")
          (cons 2 "DESC")
          (cons 70 0)
          (cons 73 0)
          (cons 74 2)
          (cons 280 0)
         )
         (list (cons 0 "ENDBLK"))
        )
       )
       ((= (strcase BLKNAME) "SUPER")
        (list
         (list
          (cons 0 "BLOCK")
          (cons 2 "super")
          (cons 70  2)
          (list 10 0.00000000 0.00000000 0.00000000)
         )
         (list
          (cons 0 "ATTDEF")
          (cons 100 "AcDbEntity")
          (cons 67 0)
          (cons 8 "0")
          (cons 100 "AcDbText")
          (list 10 0.00000000 -1.20000000 0.00000000)
          (cons 40  0.75000000)
          (cons 1 "")
          (cons 50  0.00000000)
          (cons 41  1.00000000)
          (cons 51  0.00000000)
          (cons 7 "Standard")
          (cons 71 0)
          (cons 72 4)
          (list 11 0.00000000 -1.20000000 0.00000000)
          (list 210 0.00000000 0.00000000 1.00000000)
          (cons 100 "AcDbAttributeDefinition")
          (cons 280 0)
          (cons 3 "Left superlevation")
          (cons 2 "LEFT")
          (cons 70 0)
          (cons 73 0)
          (cons 74 0)
          (cons 280 0)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 0.00000000 1.20000000 0.00000000)
          (cons 40  0.75000000)
          (cons 1 "")
          (cons 50  0.00000000)
          (cons 41  1.00000000)
          (cons 51  0.00000000)
          (cons 7 "Standard")
          (cons 71 0)
          (cons 72 4)
          (list 11 0.00000000 1.20000000 0.00000000)
          (list 210 0.00000000 0.00000000 1.00000000)
          (cons 100 "AcDbAttributeDefinition")
          (cons 280 0)
          (cons 3 "Right superlevation")
          (cons 2 "RIGHT")
          (cons 70 0)
          (cons 73 0)
          (cons 74 0)
          (cons 280 0)
         )
         (list (cons 0 "ENDBLK"))
        )
       )
       ((= (strcase BLKNAME) "STALBL")
        (list
         (list
          (cons 0 "BLOCK")
          (cons 2 "STALBL")
          (cons 70  2)
          (list 10 0.00000000 0.00000000 0.00000000)
         )
         (list
          (cons 0 "ATTDEF")
          (cons 100 "AcDbEntity")
          (cons 67 0)
          (cons 8 "0")
          (cons 100 "AcDbText")
          (list 10 -6.92857143 -1.00000000 0.00000000)
          (cons 40  2.00000000)
          (cons 1 "100")
          (cons 50  0.00000000)
          (cons 41  1.00000000)
          (cons 51  0.00000000)
          (cons 7 "Standard")
          (cons 71 0)
          (cons 72 2)
          (list 11 -1.50000000 0.00000000 0.00000000)
          (list 210 0.00000000 0.00000000 1.00000000)
          (cons 100 "AcDbAttributeDefinition")
          (cons 280 0)
          (cons 3 "STAH")
          (cons 2 "STAH")
          (cons 70 0)
          (cons 73 0)
          (cons 74 2)
          (cons 280 0)
         )
         (list
          (cons 0 "ATTDEF")
          (cons 100 "AcDbEntity")
          (cons 67 0)
          (cons 8 "0")
          (cons 100 "AcDbText")
          (list 10 1.50000000 -1.00000000 0.00000000)
          (cons 40  2.00000000)
          (cons 1 "000.000")
          (cons 50  0.00000000)
          (cons 41  1.00000000)
          (cons 51  0.00000000)
          (cons 7 "Standard")
          (cons 71 0)
          (cons 72 0)
          (list 11 1.50000000 0.00000000 0.00000000)
          (list 210 0.00000000 0.00000000 1.00000000)
          (cons 100 "AcDbAttributeDefinition")
          (cons 280 0)
          (cons 3 "STAL")
          (cons 2 "STAL")
          (cons 70 0)
          (cons 73 0)
          (cons 74 2)
          (cons 280 0)
         )
         (list
          (cons 0 "TEXT")
          (cons 100 "AcDbEntity")
          (cons 67 0)
          (cons 8 "0")
          (cons 100 "AcDbText")
          (list 10 -1.23809524 -0.85714286 0.00000000)
          (cons 40  2.00000000)
          (cons 1 "+")
          (cons 50  0.00000000)
          (cons 41  1.00000000)
          (cons 51  0.00000000)
          (cons 7 "Standard")
          (cons 71 0)
          (cons 72 4)
          (list 11 0.00000000 0.00000000 0.00000000)
          (list 210 0.00000000 0.00000000 1.00000000)
          (cons 100 "AcDbText")
          (cons 73 0)
         )
         (list (cons 0 "ENDBLK"))
        )
       )
       ((= (strcase BLKNAME) "STATICK")
        (list
         (list
          (cons 0 "BLOCK")
          (cons 2 "STATICK")
          (cons 70  0)
          (list 10 0.00000000 0.00000000 0.00000000)
         )
         (list
          (cons 0 "LINE")
          (cons 100 "AcDbEntity")
          (cons 67 0)
          (cons 8 "0")
          (cons 100 "AcDbLine")
          (list 10 0.00000000 -0.75000000 0.00000000)
          (list 11 0.00000000 0.75000000 0.00000000)
          (list 210 0.00000000 0.00000000 1.00000000)
         )
         (list (cons 0 "ENDBLK"))
        )
       )
       ((= (strcase BLKNAME) "SPOTELEVATION2")
        (list
         (list
          (cons 0 "BLOCK")
          (cons 2 "spotelevation2")
          (cons 70  2)
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 0.00207694 -1.20000180 0.00000000)
          (cons 40  0.75000000)
          (cons 1 "")
          (cons 50  6.28145452)
          (cons 41  1.00000000)
          (cons 51  0.00000000)
          (cons 7 "Standard")
          (cons 71 0)
          (cons 72 4)
          (list 11 0.00207694 -1.20000180 0.00000000)
          (list 210 0.00000000 0.00000000 1.00000000)
          (cons 100 "AcDbAttributeDefinition")
          (cons 280 0)
          (cons 3 "Elevation:")
          (cons 2 "ELEV")
          (cons 70 0)
          (cons 73 0)
          (cons 74 0)
          (cons 280 0)
         )
         (list (cons 0 "ENDBLK"))
        )
       )
       ((= (strcase BLKNAME) "SLOPE")
        (list
         (list
          (cons 0 "BLOCK")
          (cons 2 "SLOPE")
          (cons 70  2)
          (cons 4 "Slope Indicator # (Attribute)")
          (list 10 0.00000000 0.00000000 0.00000000)
         )
         (list
          (cons 0 "SOLID")
          (cons 100 "AcDbEntity")
          (cons 67 0)
          (cons 8 "0")
          (cons 100 "AcDbTrace")
          (list 10 1.50000000 -0.25000000 0.00000000)
          (list 11 2.50000000 0.00000000 0.00000000)
          (list 12 1.50000000 0.25000000 0.00000000)
          (list 13 1.50000000 0.25000000 0.00000000)
          (cons 39  0.00000000)
          (list 210 0.00000000 0.00000000 1.00000000)
         )
         (list
          (cons 0 "LINE")
          (cons 100 "AcDbEntity")
          (cons 67 0)
          (cons 8 "0")
          (cons 100 "AcDbLine")
          (list 10 -2.50000000 0.00000000 0.00000000)
          (list 11 1.50000000 0.00000000 0.00000000)
          (list 210 0.00000000 0.00000000 1.00000000)
         )
         (list
          (cons 0 "ATTDEF")
          (cons 100 "AcDbEntity")
          (cons 67 0)
          (cons 8 "0")
          (cons 100 "AcDbText")
          (list 10 0.00000000 1.20000000 0.00000000)
          (cons 40  0.75000000)
          (cons 1 "")
          (cons 50  0.00000000)
          (cons 41  1.00000000)
          (cons 51  0.00000000)
          (cons 7 "Standard")
          (cons 71 0)
          (cons 72 4)
          (list 11 0.00000000 1.20000000 0.00000000)
          (list 210 0.00000000 0.00000000 1.00000000)
          (cons 100 "AcDbAttributeDefinition")
          (cons 280 0)
          (cons 3 "Slope:")
          (cons 2 "SLOPE")
          (cons 70 0)
          (cons 73 0)
          (cons 74 0)
          (cons 280 0)
         )
         (list (cons 0 "ENDBLK"))
        )
       )
       ((= (strcase BLKNAME) "SPOTELEVATION")
        (list
         (list
          (cons 0 "BLOCK")
          (cons 2 "spotelevation")
          (cons 70  2)
          (list 10 0.00000000 0.00000000 0.00000000)
         )
         (list
          (cons 0 "ATTDEF")
          (cons 100 "AcDbEntity")
          (cons 67 0)
          (cons 8 "0")
          (cons 100 "AcDbText")
          (list 10 0.00000000 1.20000000 0.00000000)
          (cons 40  0.75000000)
          (cons 1 "")
          (cons 50  0.00000000)
          (cons 41  1.00000000)
          (cons 51  0.00000000)
          (cons 7 "Standard")
          (cons 71 0)
          (cons 72 4)
          (list 11 0.00000000 1.20000000 0.00000000)
          (list 210 0.00000000 0.00000000 1.00000000)
          (cons 100 "AcDbAttributeDefinition")
          (cons 280 0)
          (cons 3 "Elevation:")
          (cons 2 "ELEV")
          (cons 70 0)
          (cons 73 0)
          (cons 74 0)
          (cons 280 0)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list (cons 0 "ENDBLK"))
        )
       )
       ((= (strcase BLKNAME) "RFLALIGN")
        (list
         (list
          (cons 0 "BLOCK")
          (cons 2 "RFLAlign")
          (cons 70  2)
          (list 10 0.00000000 0.00000000 0.00000000)
         )
         (list
          (cons 0 "TEXT")
          (cons 100 "AcDbEntity")
          (cons 67 0)
          (cons 8 "0")
          (cons 100 "AcDbText")
          (list 10 -3.38095238 0.00000000 0.00000000)
          (cons 40  1.00000000)
          (cons 1 "HOR:")
          (cons 50  0.00000000)
          (cons 41  1.00000000)
          (cons 51  0.00000000)
          (cons 7 "Standard")
          (cons 71 0)
          (cons 72 2)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.90476190 -1.66666667 0.00000000)
          (cons 40  1.00000000)
          (cons 1 "VRT:")
          (cons 50  0.00000000)
          (cons 41  1.00000000)
          (cons 51  0.00000000)
          (cons 7 "Standard")
          (cons 71 0)
          (cons 72 2)
          (list 11 0.00000000 -1.66666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -1.19047619 -3.33333333 0.00000000)
          (cons 40  1.00000000)
          (cons 1 "E:")
          (cons 50  0.00000000)
          (cons 41  1.00000000)
          (cons 51  0.00000000)
          (cons 7 "Standard")
          (cons 71 0)
          (cons 72 2)
          (list 11 0.00000000 -3.33333333 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.33333333 -5.00000000 0.00000000)
          (cons 40  1.00000000)
          (cons 1 "OG:")
          (cons 50  0.00000000)
          (cons 41  1.00000000)
          (cons 51  0.00000000)
          (cons 7 "Standard")
          (cons 71 0)
          (cons 72 2)
          (list 11 0.00000000 -5.00000000 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 0.00000000 2.00000000 0.00000000)
          (cons 40  1.00000000)
          (cons 1 "")
          (cons 50  0.00000000)
          (cons 41  1.00000000)
          (cons 51  0.00000000)
          (cons 7 "Standard")
          (cons 71 0)
          (cons 72 1)
          (list 11 0.00000000 1.66666667 0.00000000)
          (list 210 0.00000000 0.00000000 1.00000000)
          (cons 100 "AcDbAttributeDefinition")
          (cons 280 0)
          (cons 3 "TITLE")
          (cons 2 "TITLE")
          (cons 70 0)
          (cons 73 0)
          (cons 74 1)
          (cons 280 0)
         )
         (list
          (cons 0 "ATTDEF")
          (cons 100 "AcDbEntity")
          (cons 67 0)
          (cons 8 "0")
          (cons 100 "AcDbText")
          (list 10 1.00000000 0.00000000 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "HOR")
          (cons 2 "HOR")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -1.66666667 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "VRT")
          (cons 2 "VRT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -3.33333333 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "E")
          (cons 2 "E")
          (cons 70 0)
          (cons 73 0)
          (cons 74 0)
          (cons 280 0)
         )
         (list
          (cons 0 "ATTDEF")
          (cons 100 "AcDbEntity")
          (cons 67 0)
          (cons 8 "0")
          (cons 100 "AcDbText")
          (list 10 1.00000000 -5.00000000 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "OG")
          (cons 2 "OG")
          (cons 70 0)
          (cons 73 0)
          (cons 74 0)
          (cons 280 0)
         )
         (list
          (cons 0 "TEXT")
          (cons 100 "AcDbEntity")
          (cons 67 0)
          (cons 8 "0")
          (cons 100 "AcDbText")
          (list 10 -5.09523810 -6.66666666 0.00000000)
          (cons 40  1.00000000)
          (cons 1 "CL OS:")
          (cons 50  0.00000000)
          (cons 41  1.00000000)
          (cons 51  0.00000000)
          (cons 7 "Standard")
          (cons 71 0)
          (cons 72 2)
          (list 11 0.00000000 -6.66666666 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 1.00000000 -6.66666666 0.00000000)
          (cons 40  1.00000000)
          (cons 1 "N/A")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Centerline Offset")
          (cons 2 "CLOS")
          (cons 70 0)
          (cons 73 0)
          (cons 74 0)
          (cons 280 0)
         )
         (list (cons 0 "ENDBLK"))
        )
       )
       ((= (strcase BLKNAME) "RFLPROF")
        (list
         (list
          (cons 0 "BLOCK")
          (cons 2 "rflprof")
          (cons 70  2)
          (list 10 0.00000000 0.00000000 0.00000000)
         )
         (list
          (cons 0 "ATTDEF")
          (cons 100 "AcDbEntity")
          (cons 67 0)
          (cons 8 "0")
          (cons 100 "AcDbText")
          (list 10 -4.02380952 -29.25000000 0.00000000)
          (cons 40  2.50000000)
          (cons 1 "0")
          (cons 50  0.00000000)
          (cons 41  1.00000000)
          (cons 51  0.00000000)
          (cons 7 "Standard")
          (cons 71 0)
          (cons 72 2)
          (list 11 -2.00000000 -28.00000000 0.00000000)
          (list 210 0.00000000 0.00000000 1.00000000)
          (cons 100 "AcDbAttributeDefinition")
          (cons 280 0)
          (cons 3 "Station High")
          (cons 2 "STAH")
          (cons 70 0)
          (cons 73 0)
          (cons 74 2)
          (cons 280 0)
         )
         (list
          (cons 0 "ATTDEF")
          (cons 100 "AcDbEntity")
          (cons 67 0)
          (cons 8 "0")
          (cons 100 "AcDbText")
          (list 10 2.00000000 -29.25000000 0.00000000)
          (cons 40  2.50000000)
          (cons 1 "000")
          (cons 50  0.00000000)
          (cons 41  1.00000000)
          (cons 51  0.00000000)
          (cons 7 "Standard")
          (cons 71 0)
          (cons 72 0)
          (list 11 2.00000000 -28.00000000 0.00000000)
          (list 210 0.00000000 0.00000000 1.00000000)
          (cons 100 "AcDbAttributeDefinition")
          (cons 280 0)
          (cons 3 "Station Low")
          (cons 2 "STAL")
          (cons 70 0)
          (cons 73 0)
          (cons 74 2)
          (cons 280 0)
         )
         (list
          (cons 0 "ATTDEF")
          (cons 100 "AcDbEntity")
          (cons 67 0)
          (cons 8 "0")
          (cons 100 "AcDbText")
          (list 10 -15.00000000 -1.25000000 0.00000000)
          (cons 40  2.50000000)
          (cons 1 "0.0")
          (cons 50  0.00000000)
          (cons 41  1.00000000)
          (cons 51  0.00000000)
          (cons 7 "Standard")
          (cons 71 0)
          (cons 72 0)
          (list 11 -15.00000000 0.00000000 0.00000000)
          (list 210 0.00000000 0.00000000 1.00000000)
          (cons 100 "AcDbAttributeDefinition")
          (cons 280 0)
          (cons 3 "Elevation")
          (cons 2 "ELEV")
          (cons 70 0)
          (cons 73 0)
          (cons 74 2)
          (cons 280 0)
         )
         (list
          (cons 0 "ATTDEF")
          (cons 100 "AcDbEntity")
          (cons 67 0)
          (cons 8 "0")
          (cons 100 "AcDbText")
          (list 10 -10.59523810 -4.16666666 0.00000000)
          (cons 40  2.50000000)
          (cons 1 "1.0")
          (cons 50  0.00000000)
          (cons 41  1.00000000)
          (cons 51  0.00000000)
          (cons 7 "Standard")
          (cons 71 0)
          (cons 72 2)
          (list 11 -5.00000000 -4.16666666 0.00000000)
          (list 210 0.00000000 0.00000000 1.00000000)
          (cons 100 "AcDbAttributeDefinition")
          (cons 280 0)
          (cons 3 "Vertical Exageration")
          (cons 2 "VEXAG")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -7.02380952 -8.33333333 0.00000000)
          (cons 40  2.50000000)
          (cons 1 "0")
          (cons 50  0.00000000)
          (cons 41  1.00000000)
          (cons 51  0.00000000)
          (cons 7 "Standard")
          (cons 71 0)
          (cons 72 2)
          (list 11 -5.00000000 -8.33333333 0.00000000)
          (list 210 0.00000000 0.00000000 1.00000000)
          (cons 100 "AcDbAttributeDefinition")
          (cons 280 0)
          (cons 3 "Profile Layer")
          (cons 2 "PLAYER")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -7.02380952 -12.50000000 0.00000000)
          (cons 40  2.50000000)
          (cons 1 "0")
          (cons 50  0.00000000)
          (cons 41  1.00000000)
          (cons 51  0.00000000)
          (cons 7 "Standard")
          (cons 71 0)
          (cons 72 2)
          (list 11 -5.00000000 -12.50000000 0.00000000)
          (list 210 0.00000000 0.00000000 1.00000000)
          (cons 100 "AcDbAttributeDefinition")
          (cons 280 0)
          (cons 3 "Profile Text layer")
          (cons 2 "PTLAYER")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -5.00000000 -16.66666666 0.00000000)
          (cons 40  2.50000000)
          (cons 1 "")
          (cons 50  0.00000000)
          (cons 41  1.00000000)
          (cons 51  0.00000000)
          (cons 7 "Standard")
          (cons 71 0)
          (cons 72 2)
          (list 11 -5.00000000 -16.66666666 0.00000000)
          (list 210 0.00000000 0.00000000 1.00000000)
          (cons 100 "AcDbAttributeDefinition")
          (cons 280 0)
          (cons 3 "File Name")
          (cons 2 "FNAME")
          (cons 70 1)
          (cons 73 0)
          (cons 74 0)
          (cons 280 0)
         )
         (list
          (cons 0 "ATTDEF")
          (cons 100 "AcDbEntity")
          (cons 67 0)
          (cons 8 "0")
          (cons 100 "AcDbText")
          (list 10 -10.59523810 -20.83333333 0.00000000)
          (cons 40  2.50000000)
          (cons 1 "1.0")
          (cons 50  0.00000000)
          (cons 41  1.00000000)
          (cons 51  0.00000000)
          (cons 7 "Standard")
          (cons 71 0)
          (cons 72 2)
          (list 11 -5.00000000 -20.83333333 0.00000000)
          (list 210 0.00000000 0.00000000 1.00000000)
          (cons 100 "AcDbAttributeDefinition")
          (cons 280 0)
          (cons 3 "Scale")
          (cons 2 "SCALE")
          (cons 70 1)
          (cons 73 0)
          (cons 74 0)
          (cons 280 0)
         )
         (list
          (cons 0 "TEXT")
          (cons 100 "AcDbEntity")
          (cons 67 0)
          (cons 8 "0")
          (cons 100 "AcDbText")
          (list 10 -52.04761905 -1.25000000 0.00000000)
          (cons 40  2.50000000)
          (cons 1 "Datum elevation :")
          (cons 50  0.00000000)
          (cons 41  1.00000000)
          (cons 51  0.00000000)
          (cons 7 "Standard")
          (cons 71 0)
          (cons 72 2)
          (list 11 -18.00000000 0.00000000 0.00000000)
          (list 210 0.00000000 0.00000000 1.00000000)
          (cons 100 "AcDbText")
          (cons 73 2)
         )
         (list
          (cons 0 "TEXT")
          (cons 100 "AcDbEntity")
          (cons 67 0)
          (cons 8 "0")
          (cons 100 "AcDbText")
          (list 10 -1.54761905 -29.07142857 0.00000000)
          (cons 40  2.50000000)
          (cons 1 "+")
          (cons 50  0.00000000)
          (cons 41  1.00000000)
          (cons 51  0.00000000)
          (cons 7 "Standard")
          (cons 71 0)
          (cons 72 4)
          (list 11 0.00000000 -28.00000000 0.00000000)
          (list 210 0.00000000 0.00000000 1.00000000)
          (cons 100 "AcDbText")
          (cons 73 0)
         )
         (list
          (cons 0 "LINE")
          (cons 100 "AcDbEntity")
          (cons 67 0)
          (cons 8 "0")
          (cons 100 "AcDbLine")
          (list 10 0.00000000 0.00000000 0.00000000)
          (list 11 0.00000000 -25.00000000 0.00000000)
          (list 210 0.00000000 0.00000000 1.00000000)
         )
         (list
          (cons 0 "ARC")
          (cons 100 "AcDbEntity")
          (cons 67 0)
          (cons 8 "0")
          (cons 100 "AcDbCircle")
          (list 10 0.00000000 0.00000000 0.00000000)
          (cons 40  0.50000000)
          (list 210 0.00000000 0.00000000 1.00000000)
          (cons 100 "AcDbArc")
          (cons 50  1.57079633)
          (cons 51  0.00000000)
         )
         (list
          (cons 0 "ATTDEF")
          (cons 100 "AcDbEntity")
          (cons 67 0)
          (cons 8 "0")
          (cons 100 "AcDbText")
          (list 10 -6.30952381 -25.00000000 0.00000000)
          (cons 40  2.50000000)
          (cons 1 "1")
          (cons 50  0.00000000)
          (cons 41  1.00000000)
          (cons 51  0.00000000)
          (cons 7 "Standard")
          (cons 71 0)
          (cons 72 2)
          (list 11 -5.00000000 -25.00000000 0.00000000)
          (list 210 0.00000000 0.00000000 1.00000000)
          (cons 100 "AcDbAttributeDefinition")
          (cons 280 0)
          (cons 3 "Direction (1 = Forward, -1 = Reverse)")
          (cons 2 "DIRECTION")
          (cons 70 1)
          (cons 73 0)
          (cons 74 0)
          (cons 280 0)
         )
         (list (cons 0 "ENDBLK"))
        )
       )
       ((= (strcase BLKNAME) "PVI2")
        (list
         (list
          (cons 0 "BLOCK")
          (cons 2 "PVI2")
          (cons 70  2)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  0.01254212)
          (list 210 0.00000000 0.00000000 1.00000000)
         )
         (list
          (cons 0 "LINE")
          (cons 100 "AcDbEntity")
          (cons 67 0)
          (cons 8 "0")
          (cons 100 "AcDbLine")
          (list 10 0.00000000 0.10000000 0.00000000)
          (list 11 -0.07500000 -0.05000000 0.00000000)
          (list 210 0.00000000 0.00000000 1.00000000)
         )
         (list
          (cons 0 "LINE")
          (cons 100 "AcDbEntity")
          (cons 67 0)
          (cons 8 "0")
          (cons 100 "AcDbLine")
          (list 10 0.07500000 -0.05000000 0.00000000)
          (list 11 0.00000000 0.10000000 0.00000000)
          (list 210 0.00000000 0.00000000 1.00000000)
         )
         (list
          (cons 0 "LINE")
          (cons 100 "AcDbEntity")
          (cons 67 0)
          (cons 8 "0")
          (cons 100 "AcDbLine")
          (list 10 -0.07500000 -0.05000000 0.00000000)
          (list 11 0.07500000 -0.05000000 0.00000000)
          (list 210 0.00000000 0.00000000 1.00000000)
         )
         (list
          (cons 0 "ATTDEF")
          (cons 100 "AcDbEntity")
          (cons 67 0)
          (cons 8 "0")
          (cons 100 "AcDbText")
          (list 10 -0.00402135 -0.00514594 0.00000000)
          (cons 40  0.01000000)
          (cons 1 "1")
          (cons 50  0.00000000)
          (cons 41  1.00000000)
          (cons 51  0.00000000)
          (cons 7 "Standard")
          (cons 71 0)
          (cons 72 1)
          (list 11 0.00002627 -0.00514594 0.00000000)
          (list 210 0.00000000 0.00000000 1.00000000)
          (cons 100 "AcDbAttributeDefinition")
          (cons 280 0)
          (cons 3 "K")
          (cons 2 "K")
          (cons 70 1)
          (cons 73 0)
          (cons 74 0)
          (cons 280 0)
         )
         (list
          (cons 0 "ATTDEF")
          (cons 100 "AcDbEntity")
          (cons 67 0)
          (cons 8 "0")
          (cons 100 "AcDbText")
          (list 10 0.00002627 -0.03250605 0.00000000)
          (cons 40  0.01000000)
          (cons 1 "")
          (cons 50  0.00000000)
          (cons 41  1.00000000)
          (cons 51  0.00000000)
          (cons 7 "Standard")
          (cons 71 0)
          (cons 72 1)
          (list 11 0.00002627 -0.03250605 0.00000000)
          (list 210 0.00000000 0.00000000 1.00000000)
          (cons 100 "AcDbAttributeDefinition")
          (cons 280 0)
          (cons 3 "LENGTH")
          (cons 2 "LENGTH")
          (cons 70 1)
          (cons 73 0)
          (cons 74 0)
          (cons 280 0)
         )
         (list (cons 0 "ENDBLK"))
        )
       )
       ((= (strcase BLKNAME) "POINT")
        (list
         (list
          (cons 0 "BLOCK")
          (cons 2 "point")
          (cons 70  2)
          (list 10 0.00000000 0.00000000 0.00000000)
         )
         (list
          (cons 0 "POINT")
          (cons 100 "AcDbEntity")
          (cons 67 0)
          (cons 8 "0")
          (cons 100 "AcDbPoint")
          (list 10 0.00000000 0.00000000 0.00000000)
          (list 210 0.00000000 0.00000000 1.00000000)
          (cons 50  0.00000000)
         )
         (list
          (cons 0 "ATTDEF")
          (cons 100 "AcDbEntity")
          (cons 67 0)
          (cons 8 "0")
          (cons 100 "AcDbText")
          (list 10 9.00000000 1.82142857 0.00000000)
          (cons 40  1.50000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Station")
          (cons 2 "STA")
          (cons 70 0)
          (cons 73 0)
          (cons 74 0)
          (cons 280 0)
         )
         (list
          (cons 0 "ATTDEF")
          (cons 100 "AcDbEntity")
          (cons 67 0)
          (cons 8 "0")
          (cons 100 "AcDbText")
          (list 10 9.00000000 -0.75000000 0.00000000)
          (cons 40  1.50000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Offset")
          (cons 2 "OFFSET")
          (cons 70 0)
          (cons 73 0)
          (cons 74 0)
          (cons 280 0)
         )
         (list
          (cons 0 "ATTDEF")
          (cons 100 "AcDbEntity")
          (cons 67 0)
          (cons 8 "0")
          (cons 100 "AcDbText")
          (list 10 9.00000000 -3.32142857 0.00000000)
          (cons 40  1.50000000)
          (cons 1 "")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Elevation")
          (cons 2 "ELEV")
          (cons 70 0)
          (cons 73 0)
          (cons 74 0)
          (cons 280 0)
         )
         (list
          (cons 0 "TEXT")
          (cons 100 "AcDbEntity")
          (cons 67 0)
          (cons 8 "0")
          (cons 100 "AcDbText")
          (list 10 3.00000000 1.82142857 0.00000000)
          (cons 40  1.50000000)
          (cons 1 "Sta:")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 3.00000000 -0.75000000 0.00000000)
          (cons 40  1.50000000)
          (cons 1 "O/S:")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 3.00000000 -3.32142857 0.00000000)
          (cons 40  1.50000000)
          (cons 1 "Elev:")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbText")
          (cons 73 0)
         )
         (list (cons 0 "ENDBLK"))
        )
       )
       ((= (strcase BLKNAME) "PR-CIRCLE")
        (list
         (list
          (cons 0 "BLOCK")
          (cons 2 "PR-CIRCLE")
          (cons 70  0)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  5.00000000)
          (list 210 0.00000000 0.00000000 1.00000000)
         )
         (list (cons 0 "ENDBLK"))
        )
       )
       ((= (strcase BLKNAME) "DRAWGRIDDEF")
        (list
         (list
          (cons 0 "BLOCK")
          (cons 2 "DrawGridDef")
          (cons 70  2)
          (list 10 0.00000000 0.00000000 0.00000000)
         )
         (list
          (cons 0 "CIRCLE")
          (cons 100 "AcDbEntity")
          (cons 67 0)
          (cons 8 "0")
          (cons 100 "AcDbCircle")
          (list 10 0.00000000 0.00000000 0.00000000)
          (cons 40  1.00000000)
          (list 210 0.00000000 0.00000000 1.00000000)
         )
         (list
          (cons 0 "TEXT")
          (cons 100 "AcDbEntity")
          (cons 67 0)
          (cons 8 "0")
          (cons 100 "AcDbText")
          (list 10 -2.35714286 -1.50000000 0.00000000)
          (cons 40  0.25000000)
          (cons 1 "Title Text : ")
          (cons 50  0.00000000)
          (cons 41  1.00000000)
          (cons 51  0.00000000)
          (cons 7 "Standard")
          (cons 71 0)
          (cons 72 2)
          (list 11 0.00000000 -1.50000000 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.77380952 -1.90476190 0.00000000)
          (cons 40  0.25000000)
          (cons 1 "Title Text Height : ")
          (cons 50  0.00000000)
          (cons 41  1.00000000)
          (cons 51  0.00000000)
          (cons 7 "Standard")
          (cons 71 0)
          (cons 72 2)
          (list 11 0.00000000 -1.90476190 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.71428571 -2.30952381 0.00000000)
          (cons 40  0.25000000)
          (cons 1 "Title Text Offset : ")
          (cons 50  0.00000000)
          (cons 41  1.00000000)
          (cons 51  0.00000000)
          (cons 7 "Standard")
          (cons 71 0)
          (cons 72 2)
          (list 11 0.00000000 -2.30952381 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.42857143 -2.71428571 0.00000000)
          (cons 40  0.25000000)
          (cons 1 "Base Point 'X' : ")
          (cons 50  0.00000000)
          (cons 41  1.00000000)
          (cons 51  0.00000000)
          (cons 7 "Standard")
          (cons 71 0)
          (cons 72 2)
          (list 11 0.00000000 -2.71428571 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.40476190 -3.11904762 0.00000000)
          (cons 40  0.25000000)
          (cons 1 "Base Point 'Y' : ")
          (cons 50  0.00000000)
          (cons 41  1.00000000)
          (cons 51  0.00000000)
          (cons 7 "Standard")
          (cons 71 0)
          (cons 72 2)
          (list 11 0.00000000 -3.11904762 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.57142857 -3.52380952 0.00000000)
          (cons 40  0.25000000)
          (cons 1 "Grid Width : ")
          (cons 50  0.00000000)
          (cons 41  1.00000000)
          (cons 51  0.00000000)
          (cons 7 "Standard")
          (cons 71 0)
          (cons 72 2)
          (list 11 0.00000000 -3.52380952 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.76190476 -3.92857143 0.00000000)
          (cons 40  0.25000000)
          (cons 1 "Grid Height : ")
          (cons 50  0.00000000)
          (cons 41  1.00000000)
          (cons 51  0.00000000)
          (cons 7 "Standard")
          (cons 71 0)
          (cons 72 2)
          (list 11 0.00000000 -3.92857143 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -4.39285714 -4.33333333 0.00000000)
          (cons 40  0.25000000)
          (cons 1 "Vertical Exageration : ")
          (cons 50  0.00000000)
          (cons 41  1.00000000)
          (cons 51  0.00000000)
          (cons 7 "Standard")
          (cons 71 0)
          (cons 72 2)
          (list 11 0.00000000 -4.33333333 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.78571429 -4.73809524 0.00000000)
          (cons 40  0.25000000)
          (cons 1 "Text Height : ")
          (cons 50  0.00000000)
          (cons 41  1.00000000)
          (cons 51  0.00000000)
          (cons 7 "Standard")
          (cons 71 0)
          (cons 72 2)
          (list 11 0.00000000 -4.73809524 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.72619048 -5.14285714 0.00000000)
          (cons 40  0.25000000)
          (cons 1 "Text Offset : ")
          (cons 50  0.00000000)
          (cons 41  1.00000000)
          (cons 51  0.00000000)
          (cons 7 "Standard")
          (cons 71 0)
          (cons 72 2)
          (list 11 0.00000000 -5.14285714 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -5.15476190 -5.54761905 0.00000000)
          (cons 40  0.25000000)
          (cons 1 "Horizontal Grid Spacing : ")
          (cons 50  0.00000000)
          (cons 41  1.00000000)
          (cons 51  0.00000000)
          (cons 7 "Standard")
          (cons 71 0)
          (cons 72 2)
          (list 11 0.00000000 -5.54761905 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -6.15476190 -5.95238095 0.00000000)
          (cons 40  0.25000000)
          (cons 1 "Horizontal Fine Grid Spacing : ")
          (cons 50  0.00000000)
          (cons 41  1.00000000)
          (cons 51  0.00000000)
          (cons 7 "Standard")
          (cons 71 0)
          (cons 72 2)
          (list 11 0.00000000 -5.95238095 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -6.15476190 -6.35714286 0.00000000)
          (cons 40  0.25000000)
          (cons 1 "Horizontal Grid Text Spacing : ")
          (cons 50  0.00000000)
          (cons 41  1.00000000)
          (cons 51  0.00000000)
          (cons 7 "Standard")
          (cons 71 0)
          (cons 72 2)
          (list 11 0.00000000 -6.35714286 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -4.65476190 -6.76190476 0.00000000)
          (cons 40  0.25000000)
          (cons 1 "Vertical Grid Spacing : ")
          (cons 50  0.00000000)
          (cons 41  1.00000000)
          (cons 51  0.00000000)
          (cons 7 "Standard")
          (cons 71 0)
          (cons 72 2)
          (list 11 0.00000000 -6.76190476 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -5.65476190 -7.16666667 0.00000000)
          (cons 40  0.25000000)
          (cons 1 "Vertical Fine Grid Spacing : ")
          (cons 50  0.00000000)
          (cons 41  1.00000000)
          (cons 51  0.00000000)
          (cons 7 "Standard")
          (cons 71 0)
          (cons 72 2)
          (list 11 0.00000000 -7.16666667 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -5.65476190 -7.57142857 0.00000000)
          (cons 40  0.25000000)
          (cons 1 "Vertical Grid Text Spacing : ")
          (cons 50  0.00000000)
          (cons 41  1.00000000)
          (cons 51  0.00000000)
          (cons 7 "Standard")
          (cons 71 0)
          (cons 72 2)
          (list 11 0.00000000 -7.57142857 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.58333333 -7.97619048 0.00000000)
          (cons 40  0.25000000)
          (cons 1 "Grid Layer : ")
          (cons 50  0.00000000)
          (cons 41  1.00000000)
          (cons 51  0.00000000)
          (cons 7 "Standard")
          (cons 71 0)
          (cons 72 2)
          (list 11 0.00000000 -7.97619048 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.58333333 -8.38095238 0.00000000)
          (cons 40  0.25000000)
          (cons 1 "Fine Grid Layer : ")
          (cons 50  0.00000000)
          (cons 41  1.00000000)
          (cons 51  0.00000000)
          (cons 7 "Standard")
          (cons 71 0)
          (cons 72 2)
          (list 11 0.00000000 -8.38095238 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -2.60714286 -8.78571429 0.00000000)
          (cons 40  0.25000000)
          (cons 1 "Text Layer : ")
          (cons 50  0.00000000)
          (cons 41  1.00000000)
          (cons 51  0.00000000)
          (cons 7 "Standard")
          (cons 71 0)
          (cons 72 2)
          (list 11 0.00000000 -8.78571429 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -8.25000000 -9.19047619 0.00000000)
          (cons 40  0.25000000)
          (cons 1 "Station Text Label Flag (1 = Use '+') : ")
          (cons 50  0.00000000)
          (cons 41  1.00000000)
          (cons 51  0.00000000)
          (cons 7 "Standard")
          (cons 71 0)
          (cons 72 2)
          (list 11 0.00000000 -9.19047619 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -3.08333333 -9.59523810 0.00000000)
          (cons 40  0.25000000)
          (cons 1 "Master Scale : ")
          (cons 50  0.00000000)
          (cons 41  1.00000000)
          (cons 51  0.00000000)
          (cons 7 "Standard")
          (cons 71 0)
          (cons 72 2)
          (list 11 0.00000000 -9.59523810 0.00000000)
          (list 210 0.00000000 0.00000000 1.00000000)
          (cons 100 "AcDbText")
          (cons 73 0)
         )
         (list
          (cons 0 "TEXT")
          (cons 100 "AcDbEntity")
          (cons 67 0)
          (cons 8 "0")
          (cons 100 "AcDbText")
          (list 10 -10.61904762 -10.00000001 0.00000000)
          (cons 40  0.25000000)
          (cons 1 "Direction (1 = Left to Right, -1 = Right to Left) : ")
          (cons 50  0.00000000)
          (cons 41  1.00000000)
          (cons 51  0.00000000)
          (cons 7 "Standard")
          (cons 71 0)
          (cons 72 2)
          (list 11 0.00000000 -10.00000001 0.00000000)
          (list 210 0.00000000 0.00000000 1.00000000)
          (cons 100 "AcDbText")
          (cons 73 0)
         )
         (list
          (cons 0 "ATTDEF")
          (cons 100 "AcDbEntity")
          (cons 67 0)
          (cons 8 "0")
          (cons 100 "AcDbText")
          (list 10 0.00000000 -1.50000000 0.00000000)
          (cons 40  0.25000000)
          (cons 1 "Grid Title")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Title Text")
          (cons 2 "TITLE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -1.90476190 0.00000000)
          (cons 40  0.25000000)
          (cons 1 "5.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Title Text Height")
          (cons 2 "TITLEHEIGHT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -2.30952381 0.00000000)
          (cons 40  0.25000000)
          (cons 1 "5.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Title Text Offset")
          (cons 2 "TITLEOFFSET")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -2.71428571 0.00000000)
          (cons 40  0.25000000)
          (cons 1 "0.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Base Point 'X'")
          (cons 2 "BX")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -3.11904762 0.00000000)
          (cons 40  0.25000000)
          (cons 1 "0.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Base Point 'Y'")
          (cons 2 "BY")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -3.52380952 0.00000000)
          (cons 40  0.25000000)
          (cons 1 "500.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Grid Width")
          (cons 2 "W")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -3.92857143 0.00000000)
          (cons 40  0.25000000)
          (cons 1 "200.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Grid Height")
          (cons 2 "H")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -4.33333333 0.00000000)
          (cons 40  0.25000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Exageration")
          (cons 2 "VEXAG")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -4.73809524 0.00000000)
          (cons 40  0.25000000)
          (cons 1 "2.5")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Height")
          (cons 2 "THEIGHT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -5.14285714 0.00000000)
          (cons 40  0.25000000)
          (cons 1 "2.5")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Offset")
          (cons 2 "TOFFSET")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -5.54761905 0.00000000)
          (cons 40  0.25000000)
          (cons 1 "100.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Horizontal Grid Spacing")
          (cons 2 "HINC")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -5.95238095 0.00000000)
          (cons 40  0.25000000)
          (cons 1 "20.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Horizontal Fine Grid Spacing")
          (cons 2 "HINCFINE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -6.35714286 0.00000000)
          (cons 40  0.25000000)
          (cons 1 "100.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Horizontal Grid Text Spacing")
          (cons 2 "HINCTEXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -6.76190476 0.00000000)
          (cons 40  0.25000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Grid Spacing")
          (cons 2 "VINC")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -7.16666667 0.00000000)
          (cons 40  0.25000000)
          (cons 1 "1.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Fine Grid Spacing")
          (cons 2 "VINCFINE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -7.57142857 0.00000000)
          (cons 40  0.25000000)
          (cons 1 "10.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Vertical Grid Text Spacing")
          (cons 2 "VINCTEXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -7.97619048 0.00000000)
          (cons 40  0.25000000)
          (cons 1 "PR-GRID")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Grid Layer")
          (cons 2 "LAY")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -8.38095238 0.00000000)
          (cons 40  0.25000000)
          (cons 1 "PR-GRID-MIN")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Fine Grid Layer")
          (cons 2 "LAYFINE")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -8.78571429 0.00000000)
          (cons 40  0.25000000)
          (cons 1 "PR-GRID-TXT")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Text Layer")
          (cons 2 "LAYTEXT")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -9.19047619 0.00000000)
          (cons 40  0.25000000)
          (cons 1 "0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Station Text Label Flag (1 = Use '+')")
          (cons 2 "TFLAG")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -9.59523810 0.00000000)
          (cons 40  0.25000000)
          (cons 1 "1.0")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Master Scale")
          (cons 2 "MASTER")
          (cons 70 0)
          (cons 73 0)
          (cons 74 0)
          (cons 280 0)
         )
         (list
          (cons 0 "ATTDEF")
          (cons 100 "AcDbEntity")
          (cons 67 0)
          (cons 8 "0")
          (cons 100 "AcDbText")
          (list 10 0.00000000 -10.00000001 0.00000000)
          (cons 40  0.25000000)
          (cons 1 "1")
          (cons 50  0.00000000)
          (cons 41  1.00000000)
          (cons 51  0.00000000)
          (cons 7 "Standard")
          (cons 71 0)
          (cons 72 0)
          (list 11 0.00000000 0.00000000 0.00000000)
          (list 210 0.00000000 0.00000000 1.00000000)
          (cons 100 "AcDbAttributeDefinition")
          (cons 280 0)
          (cons 3 "Direction")
          (cons 2 "DIRECTION")
          (cons 70 0)
          (cons 73 0)
          (cons 74 0)
          (cons 280 0)
         )
         (list (cons 0 "ENDBLK"))
        )
       )
       ((= (strcase BLKNAME) "FORCE")
        (list
         (list
          (cons 0 "BLOCK")
          (cons 2 "Force")
          (cons 70  2)
          (list 10 0.00000000 0.00000000 0.00000000)
         )
         (list
          (cons 0 "CIRCLE")
          (cons 100 "AcDbEntity")
          (cons 67 0)
          (cons 8 "0")
          (cons 100 "AcDbCircle")
          (list 10 7.50000000 0.00000000 0.00000000)
          (cons 40  2.50000000)
          (list 210 0.00000000 0.00000000 1.00000000)
         )
         (list
          (cons 0 "SOLID")
          (cons 100 "AcDbEntity")
          (cons 67 0)
          (cons 8 "0")
          (cons 100 "AcDbTrace")
          (list 10 2.50000000 1.00000000 0.00000000)
          (list 11 0.00000000 0.00000000 0.00000000)
          (list 12 2.50000000 -1.00000000 0.00000000)
          (list 13 2.50000000 -1.00000000 0.00000000)
          (cons 39  0.00000000)
          (list 210 0.00000000 0.00000000 1.00000000)
         )
         (list
          (cons 0 "LINE")
          (cons 100 "AcDbEntity")
          (cons 67 0)
          (cons 8 "0")
          (cons 100 "AcDbLine")
          (list 10 2.50000000 0.00000000 0.00000000)
          (list 11 5.00000000 0.00000000 0.00000000)
          (list 210 0.00000000 0.00000000 1.00000000)
         )
         (list
          (cons 0 "ATTDEF")
          (cons 100 "AcDbEntity")
          (cons 67 0)
          (cons 8 "0")
          (cons 100 "AcDbText")
          (list 10 7.50000000 0.00000000 0.00000000)
          (cons 40  1.00000000)
          (cons 1 "")
          (cons 50  4.71238898)
          (cons 41  1.00000000)
          (cons 51  0.00000000)
          (cons 7 "Standard")
          (cons 71 0)
          (cons 72 4)
          (list 11 7.50000000 0.00000000 0.00000000)
          (list 210 0.00000000 0.00000000 1.00000000)
          (cons 100 "AcDbAttributeDefinition")
          (cons 280 0)
          (cons 3 "Force")
          (cons 2 "F")
          (cons 70 0)
          (cons 73 0)
          (cons 74 0)
          (cons 280 0)
         )
         (list (cons 0 "ENDBLK"))
        )
       )
       (T
        (progn
         (alert (strcat "!!! BLOCK DOES NOT EXIST - " BLKNAME " !!!"))
         nil
        )
       )
 )
)
