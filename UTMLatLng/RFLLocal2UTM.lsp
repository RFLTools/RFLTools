;
;
;     Program written by Robert Livingston, 2021-06-11
;
;     RFL:LOCAL2UTM is a collection of routines for converting to/from project to UTM
;
;
;     RFL:SURVEY list:
;          Local Northing
;          Local Easting
;          Grid Northing
;          Grid Easting
;          Scale Factor
;          Zone LNG (i.e. "10", Vancouver)
;          Zone LAT (i.e. "U", Vancouver)
(defun RFL:SETSURVEY (/ BLOCKLIST ENT ENTLIST ENTSET GRIDEASTING GRIDNORTHING LOCALEASTING LOCALNORTHING SCALEFACTOR XREF XREFLIST ZONELAT ZONELNG)
 (setq RFL:SURVEY nil)
 (if (setq ENTSET (ssget "X" (list (cons 0 "INSERT") (cons 2 "RFLSURVEY"))))
  (progn ; Block Found
   (setq ENT nil)
   (if (/= (sslength ENTSET) 1)
    (progn
     (princ "\nMore than one RFLSURVEY block found (or none found)...  Please select desired.\n")
     (setq ENT (car (entsel "\nSelect RFL Survey block (<return> to enter manually) : ")))
    )
    (setq ENT (ssname ENTSET 0))
   )
   (setq LOCALNORTHING (atof (RFL:GETATTVALUE ENT "LOCALNORTHING")))
   (setq LOCALEASTING (atof (RFL:GETATTVALUE ENT "LOCALEASTING")))
   (setq GRIDNORTHING (atof (RFL:GETATTVALUE ENT "GRIDNORTHING")))
   (setq GRIDEASTING (atof (RFL:GETATTVALUE ENT "GRIDEASTING")))
   (setq SCALEFACTOR (atof (RFL:GETATTVALUE ENT "SCALEFACTOR")))
   (setq ZONELNG (itoa (atoi (RFL:GETATTVALUE ENT "ZONELNG"))))
   (setq ZONELAT (strcase (RFL:GETATTVALUE ENT "ZONELAT")))
   (setq RFL:SURVEY (list LOCALNORTHING LOCALEASTING GRIDNORTHING GRIDEASTING SCALEFACTOR ZONELNG ZONELAT))
  )
  (progn ; Block not in drawing
   (princ "\nRFLSurvey block not found in drawing - searching XREFS...")
   (setq XREFLIST (RFL:GETXREFS))
   (setq BLOCKLIST nil)
   (foreach XREF XREFLIST
    (if (tblsearch "BLOCK" (strcat XREF "|" "RFLSURVEY"))
     (setq BLOCKLIST (append BLOCKLIST (list XREF)))
    )
   )
   (cond ((= (length BLOCKLIST) 0)
          (setq XREF nil)
         )
         ((= (length BLOCKLIST) 1)
          (setq XREF (car BLOCKLIST))
          (princ (strcat "\nRFLSurvey block found in : " XREF))
         )
         (T
          (setq XREF (car BLOCKLIST))
          (princ (strcat "\nMor than one RFLSurvey block found, using : " XREF))
         )
   )
   (if XREF
    (progn
     (setq ENT (cdr (assoc -2 (tblsearch "BLOCK" XREF))))
     (while ENT
      (setq ENTLIST (entget ENT))
      (if (and (= "INSERT" (cdr (assoc 0 ENTLIST)))
               (= (strcase (strcat XREF "|" "RFLSURVEY")) (strcase (cdr (assoc 2 ENTLIST))))
          )
       (progn
        (setq LOCALNORTHING (atof (RFL:GETATTVALUE ENT "LOCALNORTHING")))
        (setq LOCALEASTING (atof (RFL:GETATTVALUE ENT "LOCALEASTING")))
        (setq GRIDNORTHING (atof (RFL:GETATTVALUE ENT "GRIDNORTHING")))
        (setq GRIDEASTING (atof (RFL:GETATTVALUE ENT "GRIDEASTING")))
        (setq SCALEFACTOR (atof (RFL:GETATTVALUE ENT "SCALEFACTOR")))
        (setq ZONELNG (itoa (atoi (RFL:GETATTVALUE ENT "ZONELNG"))))
        (setq ZONELAT (strcase (RFL:GETATTVALUE ENT "ZONELAT")))
        (setq RFL:SURVEY (list LOCALNORTHING LOCALEASTING GRIDNORTHING GRIDEASTING SCALEFACTOR ZONELNG ZONELAT))
       )
      )
      (setq ENT (entnext ENT))
     )
    )
   )
  )
 )
 (if (= RFL:SURVEY nil)
  (progn
   (princ "\nRFLSurvey block not found...")
   (setq RFL:SURVEY (list (getreal "\nLocal Northing : ")
                          (getreal "\nLocal Easting : ")
                          (getreal "\nGrid Northing : ")
                          (getreal "\nGrid Easting : ")
                          (getreal "\nScale Factor : ")
                          (itoa (atoi (getstring "\nZone Longitude (i.e. \"10\", Vancouver) : ")))
                          (strcase (getstring "\nZone Latitude (i.e. \"U\", Vancouver) : "))
                     )
   )
  )
 )
 RFL:SURVEY
)
(defun RFL:SURVEY2UTM (P)
 (if (not RFL:SURVEY) (RFL:SETSURVEY))
 (list (+ (/ (- (car P) (nth 1 RFL:SURVEY)) (nth 4 RFL:SURVEY)) (nth 3 RFL:SURVEY))
       (+ (/ (- (cadr P) (nth 0 RFL:SURVEY)) (nth 4 RFL:SURVEY)) (nth 2 RFL:SURVEY))
 )
)
(defun RFL:UTM2SURVEY (P)
 (if (not RFL:SURVEY) (RFL:SETSURVEY))
 (list (+ (* (- (car P) (nth 3 RFL:SURVEY)) (nth 4 RFL:SURVEY)) (nth 1 RFL:SURVEY))
       (+ (* (- (cadr P) (nth 2 RFL:SURVEY)) (nth 4 RFL:SURVEY)) (nth 0 RFL:SURVEY))
 )
)
(defun RFL:MAPLINKUTM (P / PTMP)
 (if (not RFL:SURVEY) (RFL:SETSURVEY))
 (setq PTMP (RFL:UTM2LATLNG P (nth 5 RFL:SURVEY) (nth 6 RFL:SURVEY)))
 (strcat "https://maps.google.com/?q=" (rtos (car PTMP) 2 8) "," (rtos (cadr PTMP) 2 8))
)
(defun RFL:MAPLINK (P / PTMP)
 (if (not RFL:SURVEY) (RFL:SETSURVEY))
 (setq PTMP (RFL:UTM2LATLNG (RFL:SURVEY2UTM P) (nth 5 RFL:SURVEY) (nth 6 RFL:SURVEY)))
 (strcat "https://maps.google.com/?q=" (rtos (car PTMP) 2 8) "," (rtos (cadr PTMP) 2 8))
)
(defun C:MAPLINK ()
 (command "_browser" (RFL:MAPLINK (getpoint "\nSelect point : ")))
)
(defun C:MAPLINKUTM ()
 (command "_browser" (RFL:MAPLINKUTM (getpoint "\nSelect point : ")))
)
