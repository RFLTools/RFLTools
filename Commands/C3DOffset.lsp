;
;
;     Program written by Robert Livingston, 2000/01/11
;
;     3DOFFSET is a routine for offsetting 3DPOLYLINES
;
;

(setq RFL:3DOFFSETLIST
      (list (cons "RADIO_FIXED" "1")
            (cons "RADIO_SLOPED" "0")
            (cons "RADIO_ELEV" "0")
            (cons "D1FIXED" 1.0)
            (cons "D2FIXED" 1.0)
            (cons "D1ASLOPED" 1.0)
            (cons "D1BSLOPED" 1.0)
            (cons "D2SLOPED" 1.0)
            (cons "USES1SLOPED" "1")
            (cons "USESUPER" "0")
            (cons "S1SLOPED" 2.0)
            (cons "RFLSLOPED" 0.0)
            (cons "S2SLOPED" 3.0)
            (cons "S1ELEV" 3.0)
            (cons "S1ELEVF" "VRT")
      )
)

(defun C:3DOFFSET (/ *error* 2DDIST ALC ALV ALSAVEH ALSAVES ALSAVEV
                     ANG ANG1 ANG2 ANGBASE ANGDIR ACCEPT3DOFFSET CANCEL3DOFFSET CMDECHO
                     D1A D1B D2 DCLID FIXNUMBER INITIATE OSMODE
                     P P1 P1A P2 P2A P2B P3 P3B RADIO_FIXED RADIO_SLOPED RADIO_USESD RADIO_ELEV
                     S1 S2 SIDE STAC OFFSETTYPE X Y)
;(defun C:3DOFFSET ()
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setvar "OSMODE" 0)
 (setq ALSAVEH RFL:ALIGNLIST)
 (setq ALSAVEV RFL:PVILIST)
 (setq ALSAVES RFL:SUPERLIST)

 (if (= nil RFL:3DOFFSETLIST)
  (setq RFL:3DOFFSETLIST
        (list (cons "RADIO_FIXED" "1")
              (cons "RADIO_SLOPED" "0")
              (cons "RADIO_ELEV" "0")
              (cons "D1FIXED" 1.0)
              (cons "D2FIXED" 1.0)
              (cons "D1ASLOPED" 1.0)
              (cons "D1BSLOPED" 1.0)
              (cons "D2SLOPED" 1.0)
              (cons "USES1SLOPED" "1")
              (cons "USESUPER" "0")
              (cons "S1SLOPED" 2.0)
              (cons "RFLSLOPED" 0.0)
              (cons "S2SLOPED" 3.0)
              (cons "S1ELEV" 3.0)
              (cons "S1ELEVF" "VRT")
        )
  )
 )

 (defun *error* (msg)
  (setvar "CMDECHO" CMDECHO)
  (setvar "OSMODE" OSMODE)
  (setvar "ANGBASE" ANGBASE)
  (setvar "ANGDIR" ANGDIR)
  (setq RFL:ALIGNLIST ALSAVEH)
  (setq RFL:SUPERLIST ALSAVES)
  (alert msg)
  ;(setq *error* nil)
 )

 (defun 2DDIST (P1 P2)
  (if (or (= nil P1) (= nil P2))
   (eval 0.0)
   (eval (distance (list (nth 0 P1) (nth 1 P1)) (list (nth 0 P2) (nth 1 P2))))
  )
 )

 (defun INITIATE ()
  (set_tile "RADIO_FIXED" (cdr (assoc "RADIO_FIXED" RFL:3DOFFSETLIST)))
  (set_tile "RADIO_SLOPED" (cdr (assoc "RADIO_SLOPED" RFL:3DOFFSETLIST)))
  (set_tile "RADIO_ELEV" (cdr (assoc "RADIO_ELEV" RFL:3DOFFSETLIST)))
  (set_tile "USES1SLOPED" (cdr (assoc "USES1SLOPED" RFL:3DOFFSETLIST)))
  (set_tile "USESUPER" (cdr (assoc "USESUPER" RFL:3DOFFSETLIST)))
  (cond ((= (cdr (assoc "RADIO_FIXED" RFL:3DOFFSETLIST)) "1")
         (progn
          (RADIO_FIXED)
         )
        )
        ((= (cdr (assoc "RADIO_SLOPED" RFL:3DOFFSETLIST)) "1")
         (progn
          (RADIO_SLOPED)
          (RADIO_USESUPER)
         )
        )
        ((= (cdr (assoc "RADIO_ELEV" RFL:3DOFFSETLIST)) "1")
         (progn
          (RADIO_ELEV)
         )
        )
  )
  (set_tile "D1FIXED" (rtos (cdr (assoc "D1FIXED" RFL:3DOFFSETLIST))))
  (set_tile "D2FIXED" (rtos (cdr (assoc "D2FIXED" RFL:3DOFFSETLIST))))
  (set_tile "D1ASLOPED" (rtos (cdr (assoc "D1ASLOPED" RFL:3DOFFSETLIST))))
  (set_tile "D1BSLOPED" (rtos (cdr (assoc "D1BSLOPED" RFL:3DOFFSETLIST))))
  (set_tile "D2SLOPED" (rtos (cdr (assoc "D2SLOPED" RFL:3DOFFSETLIST))))
  (set_tile "S2SLOPED" (rtos (cdr (assoc "S2SLOPED" RFL:3DOFFSETLIST))))
  (set_tile "S1SLOPED" (rtos (cdr (assoc "S1SLOPED" RFL:3DOFFSETLIST))))
  (set_tile "RFLSLOPED" (rtos (cdr (assoc "RFLSLOPED" RFL:3DOFFSETLIST))))
  (set_tile "S1ELEV" (rtos (cdr (assoc "S1ELEV" RFL:3DOFFSETLIST))))
  (set_tile "S1ELEVF" (if (= "VRT" (cdr (assoc "S1ELEVF" RFL:3DOFFSETLIST)))
                          "VRT"
                          (rtos (cdr (assoc "S1ELEVF" RFL:3DOFFSETLIST)))
                      )
  )
  (FIXNUMBER "D1FIXED")
  (FIXNUMBER "D2FIXED")
  (FIXNUMBER "D1ASLOPED")
  (FIXNUMBER "D1BSLOPED")
  (FIXNUMBER "D2SLOPED")
  (FIXNUMBER "S1SLOPED")
  (FIXNUMBER "RFLSLOPED")
  (FIXNUMBER "S2SLOPED")
  (FIXNUMBER "S1ELEV")
  (FIXNUMBERF "S1ELEVF")
  (setq RFLALIGNSLBNAME "rflAlign.slb")
  (if (= nil (findfile RFLALIGNSLBNAME))
   (progn
    (setq RFLALIGNSLBNAME (vl-filename-mktemp "rfl.slb"))
    (RFL:MAKERFLSLB RFLALIGNSLBNAME)
   )
  )
  (start_image "IMAGE1")
  (slide_image 0 0 (- (dimx_tile "IMAGE1") 1) (- (dimy_tile "IMAGE1") 1) (strcat RFLALIGNSLBNAME "(3DOFFSETFIXED)"))
  (end_image)
  (start_image "IMAGE2")
  (slide_image 0 0 (- (dimx_tile "IMAGE2") 1) (- (dimy_tile "IMAGE2") 1) (strcat RFLALIGNSLBNAME "(3DOFFSETSLOPE)"))
  (end_image)
  (start_image "IMAGE3")
  (slide_image 0 0 (- (dimx_tile "IMAGE3") 1) (- (dimy_tile "IMAGE3") 1) (strcat RFLALIGNSLBNAME "(3DOFFSETELEV)"))
  (end_image)
 )

 (defun ACCEPT3DOFFSET ()
  (setq CANCEL 0)
  (cond ((= (get_tile "RADIO_FIXED") "1")
         (setq OFFSETTYPE "FIXED")
        )
        ((= (get_tile "RADIO_SLOPED") "1")
         (setq OFFSETTYPE "SLOPED")
        )
        ((= (get_tile "RADIO_ELEV") "1")
         (setq OFFSETTYPE "ELEV")
        )
  )
  (setq RFL:3DOFFSETLIST
        (list (cons "RADIO_FIXED" (get_tile "RADIO_FIXED"))
              (cons "RADIO_SLOPED" (get_tile "RADIO_SLOPED"))
              (cons "RADIO_ELEV" (get_tile "RADIO_ELEV"))
              (cons "D1FIXED" (atof (get_tile "D1FIXED")))
              (cons "D2FIXED" (atof (get_tile "D2FIXED")))
              (cons "D1ASLOPED" (atof (get_tile "D1ASLOPED")))
              (cons "D1BSLOPED" (atof (get_tile "D1BSLOPED")))
              (cons "D2SLOPED" (atof (get_tile "D2SLOPED")))
              (cons "USES1SLOPED" (get_tile "USES1SLOPED"))
              (cons "USESUPER" (get_tile "USESUPER"))
              (cons "S1SLOPED" (atof (get_tile "S1SLOPED")))
              (cons "RFLSLOPED" (atof (get_tile "RFLSLOPED")))
              (cons "S2SLOPED" (atof (get_tile "S2SLOPED")))
              (cons "S1ELEV" (atof (get_tile "S1ELEV")))
              (cons "S1ELEVF" (if (= "VRT" (get_tile "S1ELEVF"))
                                  "VRT"
                                  (atof (get_tile "S1ELEVF"))
                              )
              )
        )
  )
  (done_dialog)
  (unload_dialog DCL_ID)
 )

 (defun CANCEL3DOFFSET ()
  (setq CANCEL 1)
  (done_dialog)
  (unload_dialog DCL_ID)
 )

 (defun RADIO_FIXED ()
  (mode_tile "D1FIXED" 0)
  (mode_tile "D2FIXED" 0)
  (mode_tile "D1ASLOPED" 1)
  (mode_tile "D1BSLOPED" 1)
  (mode_tile "D2SLOPED" 1)
  (mode_tile "S1SLOPED" 1)
  (mode_tile "S2SLOPED" 1)
  (mode_tile "USES1SLOPED" 1)
  (mode_tile "RFLSLOPED" 1)
  (mode_tile "USESUPER" 1)
  (mode_tile "S1ELEV" 1)
  (mode_tile "S1ELEVF" 1)
  (mode_tile "S1ELEVT" 1)
 )

 (defun RADIO_SLOPED ()
  (mode_tile "D1FIXED" 1)
  (mode_tile "D2FIXED" 1)
  (mode_tile "D1ASLOPED" 0)
  (mode_tile "D1BSLOPED" 0)
  (mode_tile "D2SLOPED" 0)
  (mode_tile "S2SLOPED" 0)
  (mode_tile "USES1SLOPED" 0)
  (mode_tile "USESUPER" 0)
  (mode_tile "S1ELEV" 1)
  (mode_tile "S1ELEVF" 1)
  (mode_tile "S1ELEVT" 1)
  (RADIO_USESUPER)
 )

 (defun RADIO_ELEV ()
  (mode_tile "D1FIXED" 1)
  (mode_tile "D2FIXED" 1)
  (mode_tile "D1ASLOPED" 1)
  (mode_tile "D1BSLOPED" 1)
  (mode_tile "D2SLOPED" 1)
  (mode_tile "S1SLOPED" 1)
  (mode_tile "S2SLOPED" 1)
  (mode_tile "USES1SLOPED" 1)
  (mode_tile "RFLSLOPED" 1)
  (mode_tile "USESUPER" 1)
  (mode_tile "S1ELEV" 0)
  (mode_tile "S1ELEVF" 0)
  (mode_tile "S1ELEVT" 0)
 )

 (defun RADIO_USESUPER ()
  (if (= (get_tile "USES1SLOPED") "1")
   (progn
    (mode_tile "S1SLOPED" 0)
    (mode_tile "RFLSLOPED" 1)
   )
   (progn
    (mode_tile "S1SLOPED" 1)
    (mode_tile "RFLSLOPED" 0)
   )
  )
 )

 (defun FIXNUMBER (TILE)
  (set_tile TILE (rtos (atof (get_tile TILE))))
 )

 (defun FIXNUMBERF (TILE)
  (if (= "VRT" (strcase (get_tile TILE)))
   (set_tile TILE "VRT")
   (set_tile TILE (rtos (atof (get_tile TILE))))
  )
 )

 (setq ENT (car (entsel "\nSelect 3D polyline :")))
 (if (/= ENT nil)
  (progn
   (setq ENTLIST (entget ENT))
   (if (= (cdr (assoc 0 ENTLIST)) "POLYLINE")
    (progn
     (if (/= 0 (logand (cdr (assoc 70 ENTLIST)) 8))
      (progn

       (if (= 3DOFFSETDCLNAME nil)
        (progn
         (setq 3DOFFSETDCLNAME (vl-filename-mktemp "rfl.dcl"))
         (RFL:MAKEDCL 3DOFFSETDCLNAME "3DOFFSET")
        )
        (if (= nil (findfile 3DOFFSETDCLNAME))
         (progn
          (setq 3DOFFSETDCLNAME (vl-filename-mktemp "rfl.dcl"))
          (RFL:MAKEDCL 3DOFFSETDCLNAME "3DOFFSET")
         )
        )
       )
       (setq DCL_ID (load_dialog 3DOFFSETDCLNAME))
       (if (not (new_dialog "OFFSET" DCL_ID)) (exit))

       (INITIATE)

       (action_tile "D1FIXED" "(FIXNUMBER \"D1FIXED\")")
       (action_tile "D2FIXED" "(FIXNUMBER \"D2FIXED\")")
       (action_tile "D1ASLOPED" "(FIXNUMBER \"D1ASLOPED\")")
       (action_tile "D1BSLOPED" "(FIXNUMBER \"D1BSLOPED\")")
       (action_tile "D2SLOPED" "(FIXNUMBER \"D2SLOPED\")")
       (action_tile "S1SLOPED" "(FIXNUMBER \"S1SLOPED\")")
       (action_tile "RFLSLOPED" "(FIXNUMBER \"RFLSLOPED\")")
       (action_tile "S2SLOPED" "(FIXNUMBER \"S2SLOPED\")")
       (action_tile "S1ELEV" "(FIXNUMBER \"S1ELEV\")")
       (action_tile "S1ELEVF" "(FIXNUMBERF \"S1ELEVF\")")
       (action_tile "RADIO_FIXED" "(RADIO_FIXED)")
       (action_tile "RADIO_SLOPED" "(RADIO_SLOPED)")
       (action_tile "RADIO_ELEV" "(RADIO_ELEV)")
       (action_tile "USES1SLOPED" "(RADIO_USESUPER)")
       (action_tile "USESUPER" "(RADIO_USESUPER)")
       (action_tile "OK" "(ACCEPT3DOFFSET)")
       (action_tile "CANCEL" "(CANCEL3DOFFSET)")

       (start_dialog)

       (if (= CANCEL 0)
        (progn
         (if (= OFFSETTYPE "FIXED")
          (progn
           (setq D1 (cdr (assoc "D1FIXED" RFL:3DOFFSETLIST)))
           (setq D2 (cdr (assoc "D2FIXED" RFL:3DOFFSETLIST)))
           (setq P1 nil P2 nil P3 nil)
           (setq ENT (entnext ENT))
           (setq ENTLIST (entget ENT))
           (setq P2 (cdr (assoc 10 ENTLIST)))
           (setq ENT (entnext ENT))
           (setq ENTLIST (entget ENT))
           (setq P3 (cdr (assoc 10 ENTLIST)))
           (command "._3DPOLY")
           (while (/= P2 nil)
            (if (= nil P1)
             (setq ANG1 nil)
             (progn
              (setq ANG1 (angle (list (nth 0 P1) (nth 1 P1)) (list (nth 0 P2) (nth 1 P2))))
             )
            )
            (if (= nil P3)
             (setq ANG2 nil)
             (progn
              (setq ANG2 (angle (list (nth 0 P2) (nth 1 P2)) (list (nth 0 P3) (nth 1 P3))))
             )
            )
            (if (= nil ANG1)
             (setq P1A nil P2A nil)
             (progn
              (setq P1A (list (+ (nth 0 P1)
                                 (* D2
                                    (cos (- ANG1 (/ pi 2.0)))
                                 )
                              )
                              (+ (nth 1 P1)
                                 (* D2
                                    (sin (- ANG1 (/ pi 2.0)))
                                 )
                              )
                        )
              )
              (setq P2A (list (+ (nth 0 P2)
                                 (* D2
                                    (cos (- ANG1 (/ pi 2.0)))
                                 )
                              )
                              (+ (nth 1 P2)
                                 (* D2
                                    (sin (- ANG1 (/ pi 2.0)))
                                 )
                              )
                        )
              )
             )
            )
            (if (= nil ANG2)
             (setq P2B nil P3B nil)
             (progn
              (setq P2B (list (+ (nth 0 P2)
                                 (* D2
                                    (cos (- ANG2 (/ pi 2.0)))
                                 )
                              )
                              (+ (nth 1 P2)
                                 (* D2
                                    (sin (- ANG2 (/ pi 2.0)))
                                 )
                              )
                        )
              )
              (setq P3B (list (+ (nth 0 P3)
                                 (* D2
                                    (cos (- ANG2 (/ pi 2.0)))
                                 )
                              )
                              (+ (nth 1 P3)
                                 (* D2
                                    (sin (- ANG2 (/ pi 2.0)))
                                 )
                              )
                        )
              )
             )
            )
            (if (= ANG1 nil)
             (setq P P2B)
             (if (= ANG2 nil)
              (setq P P2A)
              (setq P (inters P1A P2A P2B P3B nil))
             )
            )
            (if (= nil P)
             (setq P P2A)
            )
            (if (= nil P)
             (setq P P2B)
            )
            (setq P (list (nth 0 P)
                          (nth 1 P)
                          (- (nth 2 P2)
                             D1
                          )
                    )
            )
            (command "_NON" P)
            (setq P1 P2)
            (setq P2 P3)
            (while (and (/= P3 nil)
                        (= (2DDIST P2 P3) 0.0)
                   )
             (if (/= (cdr (assoc 0 ENTLIST)) "SEQEND")
              (progn
               (setq ENT (entnext ENT))
               (setq ENTLIST (entget ENT))
               (if (= (cdr (assoc 0 ENTLIST)) "SEQEND")
                (progn
                 (setq P3 nil)
                )
                (progn
                 (setq P3 (cdr (assoc 10 ENTLIST)))
                )
               )
              )
             )
            )
           )
           (command "")
          )
         )
         (if (= OFFSETTYPE "SLOPED")
          (progn
           (setq D1A (cdr (assoc "D1ASLOPED" RFL:3DOFFSETLIST)))
           (setq D1B (cdr (assoc "D1BSLOPED" RFL:3DOFFSETLIST)))
           (setq D2 (cdr (assoc "D2SLOPED" RFL:3DOFFSETLIST)))
           (setq S2 (cdr (assoc "S2SLOPED" RFL:3DOFFSETLIST)))
           (if (or (= (cdr (assoc "USES1SLOPED" RFL:3DOFFSETLIST)) "1")
                   (and (= (cdr (assoc "USESUPER" RFL:3DOFFSETLIST)) "1")
                        (/= RFL:SUPERLIST nil)
                        (/= RFL:ALIGNLIST nil)
                   )
               )
            (progn
             (setq P1 nil P2 nil P3 nil)
             (setq ENT (entnext ENT))
             (setq ENTLIST (entget ENT))
             (setq P2 (cdr (assoc 10 ENTLIST)))
             (setq ENT (entnext ENT))
             (setq ENTLIST (entget ENT))
             (setq P3 (cdr (assoc 10 ENTLIST)))
             (command "._3DPOLY")
             (while (/= P2 nil)
              (if (= nil P1)
               (setq ANG1 nil)
               (progn
                (setq ANG1 (angle (list (nth 0 P1) (nth 1 P1)) (list (nth 0 P2) (nth 1 P2))))
               )
              )
              (if (= nil P3)
               (setq ANG2 nil)
               (progn
                (setq ANG2 (angle (list (nth 0 P2) (nth 1 P2)) (list (nth 0 P3) (nth 1 P3))))
               )
              )
              (if (= nil ANG1)
               (setq ANG ANG2)
               (if (= nil ANG2)
                (setq ANG ANG1)
                (setq ANG (/ (+ ANG1 ANG2) 2.0))
               )
              )
              (setq ANG (- ANG (/ pi 2.0)))
              (if (= (cdr (assoc "USES1SLOPED" RFL:3DOFFSETLIST)) "1")
               (setq S1 (cdr (assoc "S1SLOPED" RFL:3DOFFSETLIST)))
               (progn
                (setq SIDE (RFL:STAOFF P2))
                (if (< (nth 1 SIDE) (cdr (assoc "RFLSLOPED" RFL:3DOFFSETLIST)))
                 (setq SIDE 0)
                 (setq SIDE 1)
                )
                (setq STAC (nth 0 (RFL:STAOFF P2)))
                (setq S1 (nth SIDE (RFL:SUPER STAC)))
                (if (= SIDE 1)
                 (setq S1 (* S1 -1.0))
                )
               )
              )
              (setq X (/ (+ (* (+ D1A
                                  D1B
                               )
                               S2
                            )
                            D2
                         )
                         (- 1.0
                            (/ (* S1
                                  S2
                               )
                               100.0
                            )
                         )
                      )
              )
              (setq Y (+ D1A
                         (* (/ S1
                               100.0
                            )
                            X
                         )
                      )
              )
              (setq P (list (+ (nth 0 P2) (* X (cos ANG)))
                            (+ (nth 1 P2) (* X (sin ANG)))
                            (- (nth 2 P2) Y)
                      )
              )
              (command "_NON" P)
              (setq P1 P2)
              (setq P2 P3)
              (while (and (/= P3 nil)
                          (= (2DDIST P2 P3) 0.0)
                     )
               (if (/= (cdr (assoc 0 ENTLIST)) "SEQEND")
                (progn
                 (setq ENT (entnext ENT))
                 (setq ENTLIST (entget ENT))
                 (if (= (cdr (assoc 0 ENTLIST)) "SEQEND")
                  (progn
                   (setq P3 nil)
                  )
                  (progn
                   (setq P3 (cdr (assoc 10 ENTLIST)))
                  )
                 )
                )
               )
              )
             )
             (command "")
            )
           )
          )
         )
         (if (= OFFSETTYPE "ELEV")
          (progn
           (setq S1 (cdr (assoc "S1ELEV" RFL:3DOFFSETLIST)))
           (if (= "VRT" (cdr (assoc "S1ELEVF" RFL:3DOFFSETLIST)))
            (progn
             (setq ALC nil)
             (princ "\nControl horizontal alignment :\n")
             (C:RALIGN)
             (if (/= nil RFL:ALIGNLIST)
              (progn
               (setq ALC RFL:ALIGNLIST)
               (princ "\nVertical alignment :\n")
               (C:RPROF)
               (if (/= nil RFL:PVILIST)
                (progn
                 (setq ALV RFL:PVILIST)
                )
               )
              )
             )
            )
           )
           (if (or (and (/= ALC nil)
                        (/= ALV nil)
                   )
                   (/= "VRT" (cdr (assoc "S1ELEVF" RFL:3DOFFSETLIST)))
               )
            (progn
             (if (= "VRT" (cdr (assoc "S1ELEVF" RFL:3DOFFSETLIST)))
              (progn
               (setq RFL:ALIGNLIST ALC)
               (setq RFL:PVILIST ALV)
              )
             )
             (setq P1 nil P2 nil P3 nil)
             (setq ENT (entnext ENT))
             (setq ENTLIST (entget ENT))
             (setq P2 (cdr (assoc 10 ENTLIST)))
             (setq ENT (entnext ENT))
             (setq ENTLIST (entget ENT))
             (setq P3 (cdr (assoc 10 ENTLIST)))
             (command "._3DPOLY")
             (while (/= P2 nil)
              (if (= nil P1)
               (setq ANG1 nil)
               (progn
                (setq ANG1 (angle (list (nth 0 P1) (nth 1 P1)) (list (nth 0 P2) (nth 1 P2))))
               )
              )
              (if (= nil P3)
               (setq ANG2 nil)
               (progn
                (setq ANG2 (angle (list (nth 0 P2) (nth 1 P2)) (list (nth 0 P3) (nth 1 P3))))
               )
              )
              (if (= nil ANG1)
               (setq ANG ANG2)
               (if (= nil ANG2)
                (setq ANG ANG1)
                (setq ANG (/ (+ ANG1 ANG2) 2.0))
               )
              )
              (setq ANG (- ANG (/ pi 2.0)))
              (if (= "VRT" (cdr (assoc "S1ELEVF" RFL:3DOFFSETLIST)))
               (progn
                (setq STAC (car (RFL:STAOFF P2)))
                (setq Y (RFL:ELEVATION STAC))
               )
               (progn
                (setq Y (cdr (assoc "S1ELEVF" RFL:3DOFFSETLIST)))
               )
              )
              (setq X (* (- (nth 2 P2)
                            Y
                         )
                         S1
                      )
              )
              (setq P (list (+ (nth 0 P2) (* X (cos ANG)))
                            (+ (nth 1 P2) (* X (sin ANG)))
                            Y
                      )
              )
              (command "_NON" P)
              (setq P1 P2)
              (setq P2 P3)
              (while (and (/= P3 nil)
                          (= (2DDIST P2 P3) 0.0)
                     )
               (if (/= (cdr (assoc 0 ENTLIST)) "SEQEND")
                (progn
                 (setq ENT (entnext ENT))
                 (setq ENTLIST (entget ENT))
                 (if (= (cdr (assoc 0 ENTLIST)) "SEQEND")
                  (progn
                   (setq P3 nil)
                  )
                  (progn
                   (setq P3 (cdr (assoc 10 ENTLIST)))
                  )
                 )
                )
               )
              )
             )
             (command "")
            )
           )
          )
         )
        )
       )
      )
      (princ "\n***** Not a 3D polyline *****")
     )
    )
    (princ "\n***** Not a 3D polyline *****")
   )
  )
 )


 (setvar "CMDECHO" CMDECHO)
 (setvar "OSMODE" OSMODE)
 (setvar "ANGBASE" ANGBASE)
 (setvar "ANGDIR" ANGDIR)
 (setq RFL:ALIGNLIST ALSAVEH)
 (setq RFL:PVILIST ALSAVEV)
 (setq RFL:SUPERLIST ALSAVES)
)
