;
;
;     Program written by Robert Livingston, 05-10-17
;
;     XSEC2FACE extrudes an end section along 2 or 3 3D polyline
;
;
;(defun C:XSEC2FACE (/ *error* ANG ANG1 ANG2 ANGBACK ANGBASE ANGDIR C CT CMDECHO ENT ENTLIST NODE ORTHOMODE OSMODE P P0 P1 P2 P3 P4 PLIST PREVENT TEMPLATE)
(defun C:XSEC2FACE ()
 (setq CMDECHO (getvar "CMDECHO"))
 (setvar "CMDECHO" 0)
 (setq ORTHOMODE (getvar "ORTHOMODE"))
 (setvar "ORTHOMODE" 0)
 (setq OSMODE (getvar "OSMODE"))
 (setvar "OSMODE" 0)
 (setq ANGBASE (getvar "ANGBASE"))
 (setvar "ANGBASE" 0.0)
 (setq ANGDIR (getvar "ANGDIR"))
 (setvar "ANGDIR" 0)

 (defun *error* (msg)
  (if (>= (atof (getvar "ACADVER")) 18.2)
   (command-s "._UCS" "P")
   (command "._UCS" "P")
  )
  (setvar "CMDECHO" CMDECHO)
  (setvar "ORTHOMODE" ORTHOMODE)
  (setvar "OSMODE" OSMODE)
  (setvar "ANGBASE" ANGBASE)
  (setvar "ANGDIR" ANGDIR)
  (princ msg)
  ;(setq *error* nil)
 )

 (command "._UNDO" "M")
 (command "._UCS" "W")

 (setq TEMPLATE nil P nil PREVENT nil)
 (setq ENT (car (entsel "\nSelect template LWPolyline : ")))
 (setq ENTLIST (entget ENT))
 (if (/= "LWPOLYLINE" (cdr (assoc 0 ENTLIST)))
  (princ "\n!!!  Entity not an LWPOLYLINE !!!")
  (progn
   (if (= 1 (rem (cdr (assoc 70 ENTLIST)) 2) )
    (setq P0 (cdr (assoc 10 ENTLIST)))
    (setq P0 nil)
   )
   (if (= nil (setq P (getpoint "\nBase point (<return> for first point in polyline) : ")))
    (setq P (cdr (assoc 10 ENTLIST)))
   )
   (foreach NODE ENTLIST
    (if (= 10 (car NODE))
     (setq TEMPLATE (append TEMPLATE (list (list (- (cadr NODE) (car P)) (- (caddr NODE) (cadr P))))))
    )
   )
   (if P0 (setq TEMPLATE (append TEMPLATE (list (list (- (car P0) (car P)) (- (cadr P0) (cadr P)))))))
   (setq PLIST nil)
   (setq ENT (car (entsel "\nSelect 3D polyline : ")))
   (setq ENTLIST (entget ENT))
   (if (= (cdr (assoc 0 ENTLIST)) "POLYLINE")
    (progn
     (if (logand (cdr (assoc 70 ENTLIST)) 8)
      (progn
       (setq ENT (entnext ENT))
       (setq ENTLIST (entget ENT))
       (while (/= "SEQEND" (cdr (assoc 0 ENTLIST)))
        (setq PLIST (append PLIST (list (cdr (assoc 10 ENTLIST)))))
        (setq ENT (entnext ENT))
        (setq ENTLIST (entget ENT))
       )
      )
     )
    )
   )
   (if (or (= TEMPLATE nil) (= PLIST nil))
    (princ "\n!!!  Problem with template and/or 3D polyline !!!")
    (progn
     (setq P1 (nth 0 PLIST))
     (setq P1 (list (car P1) (cadr P1)))
     (setq P2 (nth 1 PLIST))
     (setq P2 (list (car P2) (cadr P2)))
     (setq ANG (- (angle P1 P2) (/ pi 2.0)))
     (setq C 1)
     (while (< C (length PLIST))
      (setq ANGBACK ANG)
      (if (= C (- (length PLIST) 1))
       (progn
        (setq P1 (nth (- C 1) PLIST))
        (setq P1 (list (car P1) (cadr P1)))
        (setq P2 (nth C PLIST))
        (setq P2 (list (car P2) (cadr P2)))
        (setq ANG (- (angle P1 P2) (/ pi 2.0)))
       )
       (progn
        (setq P1 (nth (- C 1) PLIST))
        (setq P1 (list (car P1) (cadr P1)))
        (setq P2 (nth C PLIST))
        (setq P2 (list (car P2) (cadr P2)))
        (setq ANG1 (angle P1 P2))
        (setq P1 (nth C PLIST))
        (setq P1 (list (car P1) (cadr P1)))
        (setq P2 (nth (+ C 1) PLIST))
        (setq P2 (list (car P2) (cadr P2)))
        (setq ANG2 (angle P1 P2))
        (if (> (abs (- ANG1 ANG2)) pi)
         (setq ANG (- (/ (+ ANG1 ANG2) 2.0) pi))
         (setq ANG (/ (+ ANG1 ANG2) 2.0))
        )
        (setq ANG (- ANG (/ pi 2.0)))
       )
      )
      (setq P1 (list (+ (nth 0 (nth C PLIST)) (* (caar TEMPLATE) (cos ANG)))
                     (+ (nth 1 (nth C PLIST)) (* (caar TEMPLATE) (sin ANG)))
                     (+ (nth 2 (nth C PLIST)) (cadar TEMPLATE))))
      (setq P3 (list (+ (nth 0 (nth (- C 1) PLIST)) (* (caar TEMPLATE) (cos ANGBACK)))
                     (+ (nth 1 (nth (- C 1) PLIST)) (* (caar TEMPLATE) (sin ANGBACK)))
                     (+ (nth 2 (nth (- C 1) PLIST)) (cadar TEMPLATE))))
      (setq CT 1)
      ;(setq P1 (nth C PLIST))
      ;(setq P3 (nth (- C 1) PLIST))
      (while (< CT (length TEMPLATE))
       (setq P2 P1 P4 P3)
       (setq P1 (list (+ (nth 0 (nth C PLIST)) (* (nth 0 (nth CT TEMPLATE)) (cos ANG)))
                      (+ (nth 1 (nth C PLIST)) (* (nth 0 (nth CT TEMPLATE)) (sin ANG)))
                      (+ (nth 2 (nth C PLIST)) (nth 1 (nth CT TEMPLATE)))))
       (setq P3 (list (+ (nth 0 (nth (- C 1) PLIST)) (* (nth 0 (nth CT TEMPLATE)) (cos ANGBACK)))
                      (+ (nth 1 (nth (- C 1) PLIST)) (* (nth 0 (nth CT TEMPLATE)) (sin ANGBACK)))
                      (+ (nth 2 (nth (- C 1) PLIST)) (nth 1 (nth CT TEMPLATE)))))
       (entmake (list (cons 0 "3DFACE")
                      (cons 10 P1)
                      (cons 11 P2)
                      (cons 12 P4)
                      (cons 13 P3)
                      (cons 70 0)
                )
       )
       (setq ENT (entlast))(RFL:PUTPREVENT ENT PREVENT)(RFL:PUTNEXTENT PREVENT ENT)(setq PREVENT ENT)

       (setq CT (+ CT 1))
      )
      (setq C (+ C 1))
     )
    )
   )
  )
 )

 (command "._UCS" "P")
 (setvar "CMDECHO" CMDECHO)
 (setvar "ORTHOMODE" ORTHOMODE)
 (setvar "OSMODE" OSMODE)
 (setvar "ANGBASE" ANGBASE)
 (setvar "ANGDIR" ANGDIR)
)
