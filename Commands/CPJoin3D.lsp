;
;
;    Program Written by Robert Livingston 99/08/10
;    C:PJOIN3D is a utility for joining 3D Polylines
;
;
(defun C:PJOIN3D (/ *error* CLAYER CMDECHO ENT ENT1 ENT2 ENTLIST ENTLIST1 ENTLIST2 ORTHOMODE OSMODE P1 P2 P3 P4 PLIST1 PLIST2)
 (setq CMDECHO (getvar "CMDECHO"))
 (setvar "CMDECHO" 0)
 (setq CLAYER (getvar "CLAYER"))
 (setq OSMODE (getvar "OSMODE"))
 (setvar "OSMODE" 0)
 (setq ORTHOMODE (getvar "ORTHOMODE"))
 (setvar "ORTHOMODE" 0)

 (defun *error* (msg)
  (setvar "CMDECHO" CMDECHO)
  (setvar "OSMODE" OSMODE)
  (setvar "ORTHOMODE" ORTHOMODE)
  (alert msg)
  ;(setq *error* nil)
 )

 (setq ENT1 (car (entsel "\nSelect first 3D polyline or line : ")))
 (if (/= ENT1 nil)
  (progn
   (command "._LIST" ENT1)
   (setq ENTLIST1 (entget ENT1))
   (if (and (/= (cdr (assoc 0 ENTLIST1)) "POLYLINE")
            (/= (cdr (assoc 0 ENTLIST1)) "LINE"))
    (princ "\n*****  Entity not a polyline!  *****")
    (progn
     (if (and (/= (cdr (assoc 0 ENTLIST1)) "LINE")
	          (= 0 (logand (cdr (assoc 70 ENTLIST1)) 8))
         )
      (princ "\n*****  Entity not a 3d polyline or line!  *****")
      (progn
       (setq ENT2 (car (entsel "\nSelect second 3D polyline : ")))
       (if (/= ENT2 nil)
        (progn
         (command)
         (setq ENTLIST2 (entget ENT2))
         (if (and (/= (cdr (assoc 0 ENTLIST2)) "POLYLINE")
		  (/= (cdr (assoc 0 ENTLIST2)) "LINE"))
          (princ "\n*****  Entity not a polyline!  *****")
          (progn
           (if (and (/= (cdr (assoc 0 ENTLIST2)) "LINE")
		            (= 0 (logand (cdr (assoc 70 ENTLIST2)) 8))
               )
            (princ "\n*****  Entity not a 3d polyline or line!  *****")
            (progn
	     (if (= (cdr (assoc 0 ENTLIST1)) "LINE")
	      (progn
	       (setq PLIST1 (list (cdr (assoc 10 ENTLIST1)) (cdr (assoc 11 ENTLIST1))))
	      )
	      (progn
               (setq ENT (entnext ENT1))
               (setq ENTLIST (entget ENT))
               (setq PLIST1 nil)
               (while (/= (cdr (assoc 0 ENTLIST)) "SEQEND")
                (setq PLIST1 (append PLIST1 (list (cdr (assoc 10 ENTLIST)))))
                (setq ENT (entnext ENT))
                (setq ENTLIST (entget ENT))
               )
	      )
	     )
	     (if (= (cdr (assoc 0 ENTLIST2)) "LINE")
	      (progn
	       (setq PLIST2 (list (cdr (assoc 10 ENTLIST2)) (cdr (assoc 11 ENTLIST2))))
	      )
	      (progn
               (setq ENT (entnext ENT2))
               (setq ENTLIST (entget ENT))
               (setq PLIST2 nil)
               (while (/= (cdr (assoc 0 ENTLIST)) "SEQEND")
                (setq PLIST2 (append PLIST2 (list (cdr (assoc 10 ENTLIST)))))
                (setq ENT (entnext ENT))
                (setq ENTLIST (entget ENT))
               )
              )
             )
            )
           )
	   (setq P1 (car PLIST1))
           (setq P2 (last PLIST1))
           (setq P3 (car PLIST2))
           (setq P4 (last PLIST2))
           (if (= (distance P1 P3) (min (distance P1 P3) (distance P1 P4) (distance P2 P3) (distance P2 P4)))
            (progn
             (setq PLIST1 (reverse PLIST1))
            )
            (progn
             (if (= (distance P1 P4) (min (distance P1 P3) (distance P1 P4) (distance P2 P3) (distance P2 P4)))
              (progn
               (setq PLIST1 (reverse PLIST1))
               (setq PLIST2 (reverse PLIST2))
              )
              (progn
               (if (= (distance P2 P4) (min (distance P1 P3) (distance P1 P4) (distance P2 P3) (distance P2 P4)))
                (progn
                 (setq PLIST2 (reverse PLIST2))
                )
               )
              )
             )
            )
           )
           (if (= (distance (last PLIST1) (car PLIST2)) 0.0)
            (setq PLIST2 (cdr PLIST2))
           )
           (command "._ERASE" ENT1 ENT2 "")
           (setvar "CLAYER" (cdr (assoc 8 ENTLIST1)))
           (command "._3DPOLY")
           (while (/= nil PLIST1)
            (command (car PLIST1))
            (setq PLIST1 (cdr PLIST1))
           )
           (while (/= nil PLIST2)
            (command (car PLIST2))
            (setq PLIST2 (cdr PLIST2))
           )
           (command "")
           (setvar "CLAYER" CLAYER)
          )
         )
        )
       )
      )
     )
    )
   )
  )
 )

 (setvar "CMDECHO" CMDECHO)
 (setvar "OSMODE" OSMODE)
 (setvar "ORTHOMODE" ORTHOMODE)
)
