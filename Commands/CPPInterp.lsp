;
;
;   Program written by Robert Livingston, 98/06/10
;
;   PPINTERP inserts POINT blocks at elevations interpolated between two selected point blocks
;
;
(setq RFL:PPPOINTNO 1)
(princ "\nEnter NEWNUMBER to set next point number.\n")
(defun C:NEWNUMBER (/ N)
 (if (= nil RFL:PPPOINTNO)
  (setq RFL:PPPOINTNO (getint "\nEnter start point number:"))
  (progn
   (setq N (getint (strcat "\nEnter start point number <" (itoa RFL:PPPOINTNO) "> :")))
   (if (/= N nil)
    (setq RFL:PPPOINTNO N)
   )
  )
 )
)
(defun C:PPINTERP (/ *error* ANGBASE ANGDIR ATTREQ BLOCKNAME BLOCKROTATION BLOCKXSCALE BLOCKYSCALE CMDECHO DIMZIN ORTHOMODE
                     OSMODE D D1 D2 D3 D4
                     P1 ELEV1 P2 ELEV2 P3 ELEV3 P4 ELEV4 P ELEV PP ENT ENT2 ENTLIST OFFSET TMP TOL)
 (command "._UNDO" "M")
 (setq ATTREQ (getvar "ATTREQ"))
 (setq CMDECHO (getvar "CMDECHO"))
 (setvar "CMDECHO" 0)
 (setq DIMZIN (getvar "DIMZIN"))
 (setvar "DIMZIN" 0)
 (setq ORTHOMODE (getvar "ORTHOMODE"))
 (setvar "ORTHOMODE" 0)
 (setq OSMODE (getvar "OSMODE"))
 (setq ANGBASE (getvar "ANGBASE"))
 (setvar "ANGBASE" 0)
 (setq ANGDIR (getvar "ANGDIR"))
 (setvar "ANGDIR" 0)
 (setq TOL 0.000001)

 (defun *error* (msg)
  (setvar "ATTREQ" ATTREQ)
  (setvar "CMDECHO" CMDECHO)
  (setvar "DIMZIN" DIMZIN)
  (setvar "ORTHOMODE" ORTHOMODE)
  (setvar "OSMODE" OSMODE)
  (setvar "ANGBASE" ANGBASE)
  (setvar "ANGDIR" ANGDIR)
  (princ msg)
  ;(setq *error* nil)
 )
 
 (princ "\nFirst POINT block (first wil be block inserted) :")
 (setq ENT (car (entsel)))
 (setq ENTLIST (entget ENT))
 (if (= (cdr (assoc 0 ENTLIST)) "INSERT")
  (progn
   (setq BLOCKNAME (cdr (assoc 2 ENTLIST)))
   (setq BLOCKXSCALE (cdr (assoc 41 ENTLIST)))
   (setq BLOCKYSCALE (cdr (assoc 42 ENTLIST)))
   (setq BLOCKROTATION (/ (* 180.0 (cdr (assoc 50 ENTLIST))) pi))
   (setq P1 (cdr (assoc 10 ENTLIST)))
   (setq P1 (list (nth 0 P1) (nth 1 P1) 0.0))
   (setq ELEV1 nil)
   (setq ENT (entnext ENT))
   (setq ENTLIST (entget ENT))
   (while (= (cdr (assoc 0 ENTLIST)) "ATTRIB")
    (cond ((or (= (strcase (cdr (assoc 2 ENTLIST))) "ELEV") (= (strcase (cdr (assoc 2 ENTLIST))) "ELEVATION"))
           (setq ELEV1 (atof (if (= (substr (cdr (assoc 1 ENTLIST)) 1 1) "(")
                                 (substr (cdr (assoc 1 ENTLIST)) 2)
                                 (cdr (assoc 1 ENTLIST))
                             )
                       )
           )
          )
    )
    (setq ENT (entnext ENT))
    (setq ENTLIST (entget ENT))
   )
   (if (/= ELEV1 nil)
    (progn
     (princ "\nSecond POINT block:")
     (setq ENT (car (entsel)))
     (setq ENTLIST (entget ENT))
     (if (= (cdr (assoc 0 ENTLIST)) "INSERT")
      (progn
       (setq P2 (cdr (assoc 10 ENTLIST)))
       (setq P2 (list (nth 0 P2) (nth 1 P2) 0.0))
       (setq ELEV2 nil)
       (setq ENT (entnext ENT))
       (setq ENTLIST (entget ENT))
       (while (= (cdr (assoc 0 ENTLIST)) "ATTRIB")
        (cond ((or (= (strcase (cdr (assoc 2 ENTLIST))) "ELEV") (= (strcase (cdr (assoc 2 ENTLIST))) "ELEVATION"))
               (setq ELEV2 (atof (if (= (substr (cdr (assoc 1 ENTLIST)) 1 1) "(")
                                     (substr (cdr (assoc 1 ENTLIST)) 2)
                                     (cdr (assoc 1 ENTLIST))
                                 )
                           )
               )
              )
        )
        (setq ENT (entnext ENT))
        (setq ENTLIST (entget ENT))
       )
       (if (/= ELEV2 nil)
        (progn
         (princ "\nThird POINT block:")
         (setq ENT (car (entsel)))
         (if (/= ENT nil)
          (progn
           (setq ENTLIST (entget ENT))
           (if (= (cdr (assoc 0 ENTLIST)) "INSERT")
            (progn
             (setq P3 (cdr (assoc 10 ENTLIST)))
             (setq P3 (list (nth 0 P3) (nth 1 P3) 0.0))
             (setq ELEV3 nil)
             (setq ENT (entnext ENT))
             (setq ENTLIST (entget ENT))
             (while (= (cdr (assoc 0 ENTLIST)) "ATTRIB")
              (cond ((or (= (strcase (cdr (assoc 2 ENTLIST))) "ELEV") (= (strcase (cdr (assoc 2 ENTLIST))) "ELEVATION"))
                     (setq ELEV3 (atof (if (= (substr (cdr (assoc 1 ENTLIST)) 1 1) "(")
                                           (substr (cdr (assoc 1 ENTLIST)) 2)
                                           (cdr (assoc 1 ENTLIST))
                                       )
                                 )
                     )
                    )
              )
              (setq ENT (entnext ENT))
              (setq ENTLIST (entget ENT))
             )
             (if (/= ELEV3 nil)
              (progn
               (setq P1 (list (car P1) (cadr P1) ELEV1))
               (setq P2 (list (car P2) (cadr P2) ELEV2))
               (setq P3 (list (car P3) (cadr P3) ELEV3))
               (setq P (getpoint "\nEnter point:"))
               (while (/= nil P)
                (setq P (list (nth 0 P) (nth 1 P)))
                (setq ELEV (RFL:PLANEZ P P1 P2 P3))
                (setvar "OSMODE" 0)
                (setvar "ATTREQ" 0)
                (command ".INSERT"
                         BLOCKNAME
                         P
                         BLOCKXSCALE
                         BLOCKYSCALE
                         BLOCKROTATION
                )
                (setvar "ATTREQ" 1)
                (setvar "OSMODE" OSMODE)
                (setq ENT (entlast))
                (setq ENTLIST (entget ENT))
                (if (= 1 (cdr (assoc 66 ENTLIST)))
                 (progn
                  (setq ENT2 (entnext ENT))
                  (setq ENTLIST (entget ENT2))
                  (while (/= "SEQEND" (cdr (assoc 0 ENTLIST)))
                   (if (or (= "ELEV" (strcase (cdr (assoc 2 ENTLIST)))) (= "ELEVATION" (strcase (cdr (assoc 2 ENTLIST)))))
                    (if ELEV
                     (setq ENTLIST (subst (cons 1 (rtos ELEV)) (assoc 1 ENTLIST) ENTLIST))
                     (setq ENTLIST (subst (cons 1 "DIV0") (assoc 1 ENTLIST) ENTLIST))
                    )
                   )
                   (if (= "PNT" (cdr (assoc 2 ENTLIST)))
                    (setq ENTLIST (subst (cons 1 (itoa RFL:PPPOINTNO)) (assoc 1 ENTLIST) ENTLIST))
                   )
                   (if (= "DESC" (cdr (assoc 2 ENTLIST)))
                    (setq ENTLIST (subst (cons 1 "INTERPOLATED") (assoc 1 ENTLIST) ENTLIST))
                   )
                   (entmod ENTLIST)
                   (setq ENT2 (entnext ENT2))
                   (setq ENTLIST (entget ENT2))
                  )
                  (entupd ENT)
                 )
                )
                (setq RFL:PPPOINTNO (+ RFL:PPPOINTNO 1))
                (setq P (getpoint "\nEnter point:"))
               )
              )
              (princ "\n**** NO ELEVATION FOR POINT ****\n")
             )
            )
            (princ "\n**** INCORRECT POINT ****\n")
           )
          )
          (progn
           (setq P (getpoint "\nEnter point:"))
           (while (/= nil P)
            (setq P (list (nth 0 P) (nth 1 P) 0.0))
            (setq D1 (distance P1 P))
            (setq D2 (distance P P2))
            (setq D (distance P1 P2))
            (setq D3 (/ (+ (- (* D1 D1) (* D2 D2)) (* D D))
                        (* 2.0 D)
                     )
            )
            (setq D4 (/ (+ (- (* D2 D2) (* D1 D1)) (* D D))
                        (* 2.0 D)
                     )
            )
            (setq OFFSET (sqrt (abs (- (* D1 D1) (* D3 D3)))))
            (princ "\nOffset = ")
            (princ (rtos OFFSET))
            (setq ELEV (+ ELEV1 (* (/ D3 D) (- ELEV2 ELEV1))))
            (setvar "OSMODE" 0)
            (setvar "ATTREQ" 0)
            (command ".INSERT"
                     BLOCKNAME
                     P
                     BLOCKXSCALE
                     BLOCKYSCALE
                     BLOCKROTATION
            )
            (setvar "ATTREQ" 1)
            (setvar "OSMODE" OSMODE)
            (setq ENT (entlast))
            (setq ENTLIST (entget ENT))
            (if (= 1 (cdr (assoc 66 ENTLIST)))
             (progn
              (setq ENT2 (entnext ENT))
              (setq ENTLIST (entget ENT2))
              (while (/= "SEQEND" (cdr (assoc 0 ENTLIST)))
               (if (or (= "ELEV" (strcase (cdr (assoc 2 ENTLIST)))) (= "ELEVATION" (strcase (cdr (assoc 2 ENTLIST)))))
                (setq ENTLIST (subst (cons 1 (rtos ELEV)) (assoc 1 ENTLIST) ENTLIST))
               )
               (if (= "PNT" (cdr (assoc 2 ENTLIST)))
                (setq ENTLIST (subst (cons 1 (itoa RFL:PPPOINTNO)) (assoc 1 ENTLIST) ENTLIST))
               )
               (if (= "DESC" (cdr (assoc 2 ENTLIST)))
                (setq ENTLIST (subst (cons 1 "INTERPOLATED") (assoc 1 ENTLIST) ENTLIST))
               )
               (entmod ENTLIST)
               (setq ENT2 (entnext ENT2))
               (setq ENTLIST (entget ENT2))
              )
              (entupd ENT)
             )
            )
            (setq RFL:PPPOINTNO (+ RFL:PPPOINTNO 1))
            (setq P (getpoint "\nEnter point:"))
           )
          )
         )
        )
        (princ "\n**** NO ELEVATION FOR POINT ****\n")
       )
      )
      (princ "\n**** INCORRECT POINT ****\n")
     )
    )
    (princ "\n**** NO ELEVATION FOR POINT ****\n")
   )
  )
  (princ "\n**** INCORRECT POINT ****\n")
 )

 (setvar "ATTREQ" ATTREQ)
 (setvar "CMDECHO" CMDECHO)
 (setvar "DIMZIN" DIMZIN)
 (setvar "ORTHOMODE" ORTHOMODE)
 (setvar "OSMODE" OSMODE)
 (setvar "ANGBASE" ANGBASE)
 (setvar "ANGDIR" ANGDIR)
)
