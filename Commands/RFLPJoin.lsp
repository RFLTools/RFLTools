;
;
;    Program Written by Robert Livingston 99/08/10
;    RFL:PJOIN is a utility for joining Polylines
;
;
(defun RFL:PJOIN (PLINEENT ENTSET2 TOL / C CMDECHO ENT ENT2 ENTLIST ENTLIST2 ENTSET FOUND OSMODE
                                         P1 P2 P3 P4 PC PLINEENTLIST R Z)
 (setq ENTSET (ssadd))
 (setq C 0)
 (while (< C (sslength ENTSET2))
  (setq ENT (ssname ENTSET2 C))
  (setq ENTLIST (entget ENT))
  (if (or (= (cdr (assoc 0 ENTLIST)) "LINE")
          (= (cdr (assoc 0 ENTLIST)) "ARC")
          (= (cdr (assoc 0 ENTLIST)) "POLYLINE")
          (= (cdr (assoc 0 ENTLIST)) "LWPOLYLINE"))
   (progn
    (setq ENTSET (ssadd ENT ENTSET))
   )
  )
  (setq C (+ C 1))
 )
 (if (= nil PLINEENT)
  (progn
   (princ "\n*** Nothing selected ***")
  )
  (progn
   (setq PLINEENTLIST (entget PLINEENT))
   (if (= (cdr (assoc 0 PLINEENTLIST)) "LWPOLYLINE")
    (progn
     (if (/= (float (/ (cdr (assoc 70 PLINEENTLIST)) 2))
             (/ (cdr (assoc 70 PLINEENTLIST)) 2.0))
      (progn
       (princ "\n*** Entity is a closed lwpolyline ***")
      )
      (progn
       (setq Z (cdr (assoc 38 PLINEENTLIST)))
       (if (/= (ssmemb PLINEENT ENTSET) nil)
        (setq ENTSET (ssdel PLINEENT ENTSET))
       )
       (setq FOUND 1)
       (while (= FOUND 1)
        (setq FOUND 0)
        (setq C 0)
        (setq PLINEENTLIST (entget PLINEENT))
        (setq P1 (cdr (assoc 10 PLINEENTLIST)))
        (setq P2 (cdr (assoc 10 (reverse PLINEENTLIST))))
        (while (and (< C (sslength ENTSET)) (= FOUND 0))
         (setq ENT (ssname ENTSET C))
         (setq ENTLIST (entget ENT))
         (cond ((= (cdr (assoc 0 ENTLIST)) "LINE")
                (progn
                 (setq P3 (cdr (assoc 10 ENTLIST)))
                 (setq P4 (cdr (assoc 11 ENTLIST)))
                )
               )
               ((= (cdr (assoc 0 ENTLIST)) "ARC")
                (progn
                 (setq PC (cdr (assoc 10 ENTLIST)))
                 (setq R (cdr (assoc 40 ENTLIST)))
                 (setq ANG1 (cdr (assoc 50 ENTLIST)))
                 (setq ANG2 (cdr (assoc 51 ENTLIST)))
                 (setq P3 (list (+ (nth 0 PC) (* R (cos ANG1)))
                                (+ (nth 1 PC) (* R (sin ANG1)))
                                (nth 2 PC)))
                 (setq P4 (list (+ (nth 0 PC) (* R (cos ANG2)))
                                (+ (nth 1 PC) (* R (sin ANG2)))
                                (nth 2 PC)))
                )
               )
               ((= (cdr (assoc 0 ENTLIST)) "POLYLINE")
                (progn
                 (if (= (float (/ (cdr (assoc 70 ENTLIST)) 2))
                        (/ (cdr (assoc 70 ENTLIST)) 2.0))
                  (progn
                   (setq ENT2 (entnext ENT))
                   (setq ENTLIST2 (entget ENT2))
                   (setq P3 (cdr (assoc 10 ENTLIST2)))
                   (setq ENT2 (entnext ENT2))
                   (setq ENTLIST2 (entget ENT2))
                   (while (/= (cdr (assoc 0 ENTLIST2)) "SEQEND")
                    (setq P4 (cdr (assoc 10 ENTLIST2)))
                    (setq ENT2 (entnext ENT2))
                    (setq ENTLIST2 (entget ENT2))
                   )
                  )
                 )
                )
               )
               ((= (cdr (assoc 0 ENTLIST)) "LWPOLYLINE")
                (progn
                 (if (= (float (/ (cdr (assoc 70 ENTLIST)) 2))
                        (/ (cdr (assoc 70 ENTLIST)) 2.0))
                  (progn
                   (setq P3 (append (cdr (assoc 10 ENTLIST)) (list (cdr (assoc 38 ENTLIST)))))
                   (setq P4 (append (cdr (assoc 10 (reverse ENTLIST))) (list (cdr (assoc 38 ENTLIST)))))
                  )
                 )
                )
               )
         )
         (cond ((< (distance P1 (list (nth 0 P3) (nth 1 P3))) TOL)
                (progn
                 (setq ENTSET (ssdel ENT ENTSET))
                 (setq FOUND 1)
                 (setq ENT (RFL:ELEVFIX ENT Z))
                 (setq PLINEENTLIST (subst (list 10 (nth 0 P3) (nth 1 P3)) (assoc 10 PLINEENTLIST) PLINEENTLIST))
                 (entmod PLINEENTLIST)
                 (entupd PLINEENT)
                 (command "._PEDIT" PLINEENT "J" ENT "" "X")
                )
               )
               ((< (distance P1 (list (nth 0 P4) (nth 1 P4))) TOL)
                (progn
                 (setq ENTSET (ssdel ENT ENTSET))
                 (setq FOUND 1)
                 (setq ENT (RFL:ELEVFIX ENT Z))
                 (setq PLINEENTLIST (subst (list 10 (nth 0 P4) (nth 1 P4)) (assoc 10 PLINEENTLIST) PLINEENTLIST))
                 (entmod PLINEENTLIST)
                 (entupd PLINEENT)
                 (command "._PEDIT" PLINEENT "J" ENT "" "X")
                )
               )
               ((< (distance P2 (list (nth 0 P3) (nth 1 P3))) TOL)
                (progn
                 (setq ENTSET (ssdel ENT ENTSET))
                 (setq FOUND 1)
                 (setq ENT (RFL:ELEVFIX ENT Z))
                 (setq PLINEENTLIST (reverse PLINEENTLIST))
                 (setq PLINEENTLIST (subst (list 10 (nth 0 P3) (nth 1 P3)) (assoc 10 PLINEENTLIST) PLINEENTLIST))
                 (setq PLINEENTLIST (reverse PLINEENTLIST))
                 (entmod PLINEENTLIST)
                 (entupd PLINEENT)
                 (command "._PEDIT" PLINEENT "J" ENT "" "X")
                )
               )
               ((< (distance P2 (list (nth 0 P4) (nth 1 P4))) TOL)
                (progn
                 (setq ENTSET (ssdel ENT ENTSET))
                 (setq FOUND 1)
                 (setq ENT (RFL:ELEVFIX ENT Z))
                 (setq PLINEENTLIST (reverse PLINEENTLIST))
                 (setq PLINEENTLIST (subst (list 10 (nth 0 P4) (nth 1 P4)) (assoc 10 PLINEENTLIST) PLINEENTLIST))
                 (setq PLINEENTLIST (reverse PLINEENTLIST))
                 (entmod PLINEENTLIST)
                 (entupd PLINEENT)
                 (command "._PEDIT" PLINEENT "J" ENT "" "X")
                )
               )
         )
         (setq C (+ C 1))
        )
       )
      )
     )
    )
    (progn
     (princ "\n*** Entity not a LWPOLYLINE ***")
    )
   )
  )
 )
 ENTSET
)
