;
;
;     Program written by Robert Livingston, 2000/01/11
;
;     PPLINE is a routine for creating 3D polylines from point block to point block
;
;
(setq RFL:PPLINEDELTA 0.0)
(defun C:PPLINEM (/ C CMDECHO ELEV ENT ENTLIST ENTSET GETPT OSMODE ORTHOMODE POINTLIST PT PT1 TMP Z)
 (setq CMDECHO (getvar "CMDECHO"))
 (setvar "CMDECHO" 0)
 (setq OSMODE (getvar "OSMODE"))
 (setvar "OSMODE" 0)
 (setq ORTHOMODE (getvar "ORTHOMODE"))
 (setvar "ORTHOMODE" 0)

 (setq TMP (getreal (strcat "\nEnter delta elevation <" (rtos RFL:PPLINEDELTA) "> :")))
 (if (/= TMP nil)
  (progn
   (setq RFL:PPLINEDELTA TMP)
  )
 )

 (defun GETPT (ENT / ENTLIST PT Z)
  (setq PT nil Z nil)
  (setq ENTLIST (entget ENT))
  (if (= (cdr (assoc 0 ENTLIST)) "AECC_POINT")
   (progn
    (setq PT (cdr (assoc 11 ENTLIST)))
    (setq Z (nth 2 PT))
    (setq PT (list (nth 0 PT) (nth 1 PT)))
   )
   (if (= (cdr (assoc 0 ENTLIST)) "AECC_COGO_POINT")
    (progn
     (setq PT (vlax-get-property (vlax-ename->vla-object ENT) "Location"))
     (setq PT (vlax-variant-value PT))
     (setq Z (vlax-safearray-get-element PT 2))
     (setq PT (list (vlax-safearray-get-element PT 0) (vlax-safearray-get-element PT 1)))
    )
    (if (= "INSERT" (cdr (assoc 0 ENTLIST)))
     (progn
      (setq PT (cdr (assoc 10 ENTLIST)))
      (setq PT (list (nth 0 PT) (nth 1 PT)))
      (if (= 1 (cdr (assoc 66 ENTLIST)))
       (progn
        (setq ENT (entnext ENT))
        (setq ENTLIST (entget ENT))
        (while (/= (cdr (assoc 0 ENTLIST)) "SEQEND")
         (if (or (= (cdr (assoc 2 ENTLIST)) "ELEV")
                 (= (cdr (assoc 2 ENTLIST)) "ELEVATION")
                 (= (cdr (assoc 2 ENTLIST)) "Z"))
          (progn
           (if (= (substr (cdr (assoc 1 ENTLIST)) 1 1) "(")
            (progn
             (setq Z (atof (substr (cdr (assoc 1 ENTLIST)) 2)))
            )
            (progn
             (setq Z (atof (cdr (assoc 1 ENTLIST))))
            )
           )
          )
         )
         (setq ENT (entnext ENT))
         (setq ENTLIST (entget ENT))
        )
       )
      )
     )
    )
   )
  )
  (if (= Z nil)
   (eval nil)
   (setq PT (list (nth 0 PT) (nth 1 PT) Z))
  )
 )

 (setq PT1 nil)
 (while (= PT1 nil)
  (setq PT1 (GETPT (car (entsel "\nSelect first spot elevation block :"))))
  (if (= PT1 nil) (princ "\n\nNo elevation found for point..."))
 )
 (princ "\n\nSelect connecting points :\n")
 (setq ENTSET (ssget))
 (setq POINTLIST nil)
 (setq C 0)
 (while (< C (sslength ENTSET))
  (setq ENT (ssname ENTSET C))
  (setq PT (GETPT ENT))
  (if (/= PT nil)
   (setq POINTLIST (append POINTLIST (list PT)))
  )
  (setq C (+ C 1))
 )
 (if (/= nil POINTLIST)
  (progn
   (command "._3DPOLY" (list (nth 0 PT1) (nth 1 PT1) (+ RFL:PPLINEDELTA (nth 2 PT1))))
   (while (/= nil POINTLIST)
    (setq POINTLIST (vl-sort POINTLIST
                             (function (lambda (e1 e2)
                                               (< (distance e1 PT1)
                                                  (distance e2 PT1)
                                               )
                                       )
                             )
                    )
    )
    (setq PT (car POINTLIST))
    (if (> (distance PT1 PT) 0.0)
     (command (list (nth 0 PT) (nth 1 PT) (+ RFL:PPLINEDELTA (nth 2 PT))))
    )
    (setq PT1 PT)
    (setq POINTLIST (cdr POINTLIST))
   )
   (command "")
  )
 )

 (setvar "CMDECHO" CMDECHO)
 (setvar "OSMODE" OSMODE)
 (setvar "ORTHOMODE" ORTHOMODE)
 T
)
