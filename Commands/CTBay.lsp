;
;
;   Program written by Robert Livingston, 00/08/03
;
;   TBAY is a utility for drawing tangent turn bays
;
;
(defun C:TBAY (/ ACCEPTTBAY ANG ANGBASE ANGDIR CANCEL CANCELTBAY CMDECHO DCL_ID DIMZIN
                 ENT ENTLIST FIXN L OSMODE P P1 P2 X Y)
 (setq CMDECHO (getvar "CMDECHO"))
 (setvar "CMDECHO" 0)
 (setq DIMZIN (getvar "DIMZIN"))
 (setvar "DIMZIN" 0)
 (setq OSMODE (getvar "OSMODE"))
 (setvar "OSMODE" 0)
 (setq ANGBASE (getvar "ANGBASE"))
 (setvar "ANGBASE" 0.0)
 (setq ANGDIR (getvar "ANGDIR"))
 (setvar "ANGDIR" 0)

 (defun ACCEPTTBAY ()
  (setq CANCEL 0)
  (setq TBAYRADIUS (atof (get_tile "RADIUS")))
  (setq TBAYDELTA (angtof (get_tile "DELTA")))
  (setq TBAYOFFSET (atof (get_tile "OFFSET")))
  (setq TBAYLS (atof (get_tile "LS")))
  (setq TBAYLEFT (get_tile "LEFT"))
  (done_dialog)
 )

 (defun CANCELTBAY ()
  (setq CANCEL 1)
  (done_dialog)
 )

 (defun FIXN (KEY / TMP)
  (if (or (= KEY "RADIUS") (= KEY "OFFSET") (= KEY "LS"))
   (progn
    (set_tile KEY (rtos (atof (get_tile KEY))))
   )
   (if (= KEY "DELTA")
    (progn
     (set_tile KEY (angtos (angtof (get_tile KEY))))
    )
   )
  )
 )

 (if (= TBAYDCLNAME nil)
  (progn
   (setq TBAYDCLNAME (vl-filename-mktemp "rfl.dcl"))
   (RFL:MAKEDCL TBAYDCLNAME "TBAY")
  )
  (if (= nil (findfile TBAYDCLNAME))
   (progn
    (setq TBAYDCLNAME (vl-filename-mktemp "rfl.dcl"))
    (RFL:MAKEDCL TBAYDCLNAME "TBAY")
   )
  )
 )


 (setq DCL_ID (load_dialog TBAYDCLNAME))
 (if (not (new_dialog "TBAY" DCL_ID)) (exit))

 (if (= TBAYRADIUS nil)
  (setq TBAYRADIUS 150.0)
 )
 (set_tile "RADIUS" (rtos TBAYRADIUS))
 (if (= TBAYDELTA nil)
  (setq TBAYDELTA (angtof "5"))
 )
 (set_tile "DELTA" (angtos TBAYDELTA))
 (if (= TBAYOFFSET nil)
  (setq TBAYOFFSET 3.5)
 )
 (set_tile "OFFSET" (rtos TBAYOFFSET))
 (if (= TBAYLS nil)
  (setq TBAYLS 60.0)
 )
 (set_tile "LS" (rtos TBAYLS))
 (if (= TBAYLEFT nil)
  (setq TBAYLEFT "1")
 )
 (if (= TBAYLEFT "1")
  (progn
   (set_tile "LEFT" "1")
   (set_tile "RIGHT" "0")
  )
  (progn
   (set_tile "LEFT" "0")
   (set_tile "RIGHT" "1")
  )
 )

 (action_tile "RADIUS" "(FIXN \"RADIUS\")")
 (action_tile "DELTA" "(FIXN \"DELTA\")")
 (action_tile "OFFSET" "(FIXN \"OFFSET\")")
 (action_tile "LS" "(FIXN \"LS\")")
 (action_tile "OK" "(ACCEPTTBAY)")
 (action_tile "CANCEL" "(CANCELTBAY)")

 (start_dialog)
 (unload_dialog DCL_ID)

 (if (= CANCEL 0)
  (progn
   (setq ENT (entsel "\nSelect start line :"))
   (if (/= ENT nil)
    (progn
     (setq P (nth 1 ENT))
     (setq P (list (nth 0 P) (nth 1 P) 0.0))
     (setq ENT (nth 0 ENT))
     (setq ENTLIST (entget ENT))
     (if (/= (cdr (assoc 0 ENTLIST)) "LINE")
      (princ "\n*** ENTITY NOT A LINE ***")
      (progn
       (setq P1 (cdr (assoc 10 ENTLIST)))
       (setq P1 (list (nth 0 P1) (nth 1 P1) 0.0))
       (setq P2 (cdr (assoc 11 ENTLIST)))
       (setq P2 (list (nth 0 P2) (nth 1 P2) 0.0))
       (if (< (distance P P1) (distance P P2))
        (progn
         (setq P P1)
         (setq ANG (angle P2 P1))
        )
        (progn
         (setq P P2)
         (setq ANG (angle P1 P2))
        )
       )
       (setq L (/ (- TBAYOFFSET (* 2.0 TBAYRADIUS (- 1.0 (cos TBAYDELTA)))) (sin TBAYDELTA)))
       (setq X (* TBAYRADIUS (sin TBAYDELTA)))
       (setq Y (* TBAYRADIUS (- 1.0 (cos TBAYDELTA))))
       (if (= TBAYLEFT "1")
        (progn
         (setq P2 (list (+ (nth 0 P) (* X (cos ANG)) (* Y -1.0 (sin ANG)))
                        (+ (nth 1 P) (* X (sin ANG)) (* Y (cos ANG)))
                  )
         )
         (command "._ARC" P "E" P2 "R" TBAYRADIUS)
         (setq P P2)
         (setq P2 (list (+ (nth 0 P) (* L (cos (+ ANG TBAYDELTA))))
                        (+ (nth 1 P) (* L (sin (+ ANG TBAYDELTA))))
                  )
         )
         (command "._LINE" P P2 "")
         (setq P P2)
         (setq P2 (list (+ (nth 0 P) (* X (cos ANG)) (* Y -1.0 (sin ANG)))
                        (+ (nth 1 P) (* X (sin ANG)) (* Y (cos ANG)))
                  )
         )
         (command "._ARC" P2 "E" P "R" TBAYRADIUS)
         (setq P P2)
        )
        (progn
         (setq Y (* -1.0 Y))
         (setq P2 (list (+ (nth 0 P) (* X (cos ANG)) (* Y -1.0 (sin ANG)))
                        (+ (nth 1 P) (* X (sin ANG)) (* Y (cos ANG)))
                  )
         )
         (command "._ARC" P2 "E" P "R" TBAYRADIUS)
         (setq P P2)
         (setq P2 (list (+ (nth 0 P) (* L (cos (- ANG TBAYDELTA))))
                        (+ (nth 1 P) (* L (sin (- ANG TBAYDELTA))))
                  )
         )
         (command "._LINE" P P2 "")
         (setq P P2)
         (setq P2 (list (+ (nth 0 P) (* X (cos ANG)) (* Y -1.0 (sin ANG)))
                        (+ (nth 1 P) (* X (sin ANG)) (* Y (cos ANG)))
                  )
         )
         (command "._ARC" P "E" P2 "R" TBAYRADIUS)
         (setq P P2)
        )
       )
       (if (> TBAYLS 0.0)
        (progn
         (setq P2 (list (+ (nth 0 P) (* TBAYLS (cos ANG)))
                        (+ (nth 1 P) (* TBAYLS (sin ANG)))
                  )
         )
         (command "._LINE" P P2 "")
         (setq P P2)
        )
       )
      )
     )
    )
   )
  )
 )

 (setvar "CMDECHO" CMDECHO)
 (setvar "DIMZIN" DIMZIN)
 (setvar "OSMODE" OSMODE)
 (setvar "ANGBASE" ANGBASE)
 (setvar "ANGDIR" ANGDIR)
)
