;
;
;     Program written by Robert Livingston, 2015/03/16
;
;     BESTARC is a utility for finding best fit arc along a selected polyline
;
;
(defun C:BESTARC (/ *error* ANG1 ANG2 ANGBASE ANGDIR ASKFLAG ATTREQ C C1 C2 CMDECHO E ENT ENTLIST ORTHOMODE OSMODE P P1 P2 PC PLIST R TMP)
 (setq ATTREQ (getvar "ATTREQ"))
 (setvar "ATTREQ" 0)
 (setq ANGBASE (getvar "ANGBASE"))
 (setvar "ANGBASE" 0.0)
 (setq ANGDIR (getvar "ANGDIR"))
 (setvar "ANGDIR" 1)
 (setq CMDECHO (getvar "CMDECHO"))
 (setvar "CMDECHO" 0)
 (setq OSMODE (getvar "OSMODE"))
 (setvar "OSMODE" 0)
 (setq ORTHOMODE (getvar "ORTHOMODE"))
 (setvar "ORTHOMODE" 0)
 (setq ASKFLAG nil)

 (defun *error* (msg)
  (setvar "ATTREQ" ATTREQ)
  (setvar "ANGBASE" ANGBASE)
  (setvar "ANGDIR" ANGDIR)
  (setvar "CMDECHO" CMDECHO)
  (setvar "OSMODE" OSMODE)
  (setvar "ORTHOMODE" ORTHOMODE)
  (print msg)
 )

 (setq PLIST nil)
 (setq E nil)
 ;(setq ENT (car (entsel "\nSelect polyline : ")))
 (setq ENT (car (nentsel "\nSelect polyline to fit arc : ")))
 (if (= "VERTEX" (cdr (assoc 0 (entget ENT))))
  (setq ENT (cdr (assoc 330 (entget ENT))))
 )
 (if (/= (setq PLIST (RFL:GETPLIST2D ENT)) nil)
  (progn
   (setq P1 (getpoint "\nPick point near desired start vertex (<return> for entire polyline) : "))
   (if (= P1 nil)
    (setq ASKFLAG T)
    (progn
     (setq P2 (getpoint "\nPick point near desired end vertex : "))
     (if (/= P2 nil)
      (setq PLIST (RFL:GETSUBPLIST PLIST P1 P2))
     )
    )
   )
   (if (>= (length PLIST) 2)
    (progn
     (setq TMP (RFL:BESTARC PLIST nil))
     (setq R (getreal (strcat "\nRadius <" (rtos (RFL:RADIUS (car TMP) (cadr TMP) (caddr TMP))) "> : ")))
     (if (/= nil R) (setq TMP (RFL:BESTARC PLIST R)))
     (if ASKFLAG
      (progn
       (initget "Yes No")
       (if (= (getkword "\nHold endpoints (Yes/<No>) : ") "Yes")
        (setq TMP (list (car PLIST) (last PLIST) (* (RFL:SIGN (caddr TMP)) (RFL:BULGE (car PLIST) (last PLIST) R)) (cadddr TMP)))
       )
      )
     )
     (setq E (cadddr TMP))
     (if (> (abs (caddr TMP)) TOL)
      (progn
       (setq PC (RFL:CENTER (car TMP) (cadr TMP) (caddr TMP)))
       (setq R (RFL:RADIUS (car TMP) (cadr TMP) (caddr TMP)))
       (if (> (caddr TMP) 0.0)
        (progn
         (setq ANG1 (angle PC (car TMP)))
         (setq ANG2 (angle PC (cadr TMP)))
        )
        (progn
         (setq ANG2 (angle PC (car TMP)))
         (setq ANG1 (angle PC (cadr TMP)))
        )
       )
       (setq ENTLIST (list (cons 0 "ARC")
                           (list 10 (car PC) (cadr PC) 0.0)
                           (cons 40 R)
                           (cons 50 ANG1)
                           (cons 51 ANG2)
                     )
       )
       (entmake ENTLIST)
       (if E (princ (strcat "\nMax Offset = " (rtos E) "\n"))) 
      )
      (progn
       (setq ENTLIST (list (cons 0 "LINE")
                           (list 10 (caar TMP) (cadar TMP) 0.0)
                           (list 11 (caadr TMP) (cadadr TMP) 0.0)
                     )
       )
       (entmake ENTLIST)
      )
     )
    )
   )
  )
 )

 (setvar "ATTREQ" ATTREQ)
 (setvar "ANGBASE" ANGBASE)
 (setvar "ANGDIR" ANGDIR)
 (setvar "CMDECHO" CMDECHO)
 (setvar "OSMODE" OSMODE)
 (setvar "ORTHOMODE" ORTHOMODE)
 E
)
