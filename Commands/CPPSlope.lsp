;
;
;     Program written by Robert Livingston, 99/05/28
;
;     PPSLOPE inserts a slope block from point block to point block
;
;     Modified 2011/09/20 to permitting selecting point entities
;
(if (= nil RFL:PPSLOPESCALE) (setq RFL:PPSLOPESCALE 1.0))
(defun C:PPSLOPE (/ *error* ANGBASE ANGDIR ATTREQ CMDECHO DIMZIN ELEV1 ELEV2 ENT ENT2 ENTLIST GRADE OSMODE PT PT1 PT2 PTMID)
;(defun C:PPSLOPE ()
 (setq CMDECHO (getvar "CMDECHO"))
 (setvar "CMDECHO" 0)
 (setq OSMODE (getvar "OSMODE"))
 (setq ATTREQ (getvar "ATTREQ"))
 (setq DIMZIN (getvar "DIMZIN"))
 (setq ANGBASE (getvar "ANGBASE"))
 (setvar "ANGBASE" 0.0)
 (setq ANGDIR (getvar "ANGDIR"))
 (setvar "ANGDIR" 0)
 (vl-load-com)

 (defun *error* (msg)
  (if (>= (atof (getvar "ACADVER")) 18.2)
   (command-s "._UCS" "P")
   (command "._UCS" "P")
  )
  (setvar "CMDECHO" CMDECHO)
  (setvar "ATTREQ" ATTREQ)
  (setvar "ANGBASE" ANGBASE)
  (setvar "ANGDIR" ANGDIR)
  ;(setq *error* nil)
  (print msg)
 )
 
 (setq ACTIVEDOC (vla-get-activedocument (vlax-get-acad-object)))
 (setq ACTIVESPC
       (vlax-get-property ACTIVEDOC
        (if (or (eq acmodelspace (vla-get-activespace ACTIVEDOC)) (eq :vlax-true (vla-get-mspace ACTIVEDOC)))
         'modelspace
         'paperspace
        )
       )
 )

 (command "._UCS" "W")

 (if (= nil RFL:PPSLOPEBLOCKNAME)
;  (setq RFL:PPSLOPEBLOCKNAME (getstring "\nEnter slope block name :"))
  (setq RFL:PPSLOPEBLOCKNAME "PPSLOPE")
 )

 (setq ELEV1 nil)
 (princ "\nSelect first spot elevation block :")
 (setq ENTLIST (entget (setq ENT (car (entsel)))))
 (if (and (= "INSERT" (cdr (assoc 0 ENTLIST))) (= 1 (cdr (assoc 66 ENTLIST))))
  (progn
   (setq PT1 (cdr (assoc 10 ENTLIST))
         PT1 (list (car PT1) (cadr PT1))
         ENT2 (entnext ENT)
         ENTLIST2 (entget ENT2)
   )
   (while (= "ATTRIB" (cdr (assoc 0 ENTLIST2)))
    (if (or (= "Z" (strcase (cdr (assoc 2 ENTLIST2))))
            (= "ELEV" (strcase (cdr (assoc 2 ENTLIST2))))
            (= "ELEVATION" (strcase (cdr (assoc 2 ENTLIST2))))
        )
     (setq ELEV1 (atof (cdr (assoc 1 ENTLIST2))))
    )
    (setq ENTLIST2 (entget (setq ENT2 (entnext ENT2))))
   )
  )
  (if (= "POINT" (cdr (assoc 0 ENTLIST)))
   (setq PT1 (cdr (assoc 10 ENTLIST))
         ELEV1 (last (cdr (assoc 10 ENTLIST)))
         PT1 (list (car PT1) (cadr PT1))
   )
   (if (= "AECC_POINT" (cdr (assoc 0 ENTLIST)))
    (setq PT1 (cdr (assoc 11 ENTLIST))
          ELEV1 (nth 2 PT1)
          PT1 (list (car PT1) (cadr PT1))
    )
    (if (= "AECC_COGO_POINT" (cdr (assoc 0 ENTLIST)))
     (setq PT1 (vlax-get-property (vlax-ename->vla-object ENT) "Location")
           PT1 (vlax-variant-value PT1)
           ELEV1 (vlax-safearray-get-element PT1 2)
           PT1 (list (vlax-safearray-get-element PT1 0) (vlax-safearray-get-element PT1 1))
     )
    )
   )
  )
 )
 (setq ELEV2 nil)
 (princ "\nSelect second spot elevation block :")
 (setq ENTLIST (entget (setq ENT (car (entsel)))))
 (if (and (= "INSERT" (cdr (assoc 0 ENTLIST))) (= 1 (cdr (assoc 66 ENTLIST))))
  (progn
   (setq PT2 (cdr (assoc 10 ENTLIST))
         PT2 (list (car PT2) (cadr PT2))
         ENT2 (entnext ENT)
         ENTLIST2 (entget ENT2)
   )
   (while (= "ATTRIB" (cdr (assoc 0 ENTLIST2)))
    (if (or (= "Z" (strcase (cdr (assoc 2 ENTLIST2))))
            (= "ELEV" (strcase (cdr (assoc 2 ENTLIST2))))
            (= "ELEVATION" (strcase (cdr (assoc 2 ENTLIST2))))
        )
     (setq ELEV2 (atof (cdr (assoc 1 ENTLIST2))))
    )
    (setq ENTLIST2 (entget (setq ENT2 (entnext ENT2))))
   )
  )
  (if (= "POINT" (cdr (assoc 0 ENTLIST)))
   (setq PT2 (cdr (assoc 10 ENTLIST))
         ELEV2 (last (cdr (assoc 10 ENTLIST)))
         PT2 (list (car PT2) (cadr PT2))
   )
   (if (= "AECC_POINT" (cdr (assoc 0 ENTLIST)))
    (setq PT2 (cdr (assoc 11 ENTLIST))
          ELEV2 (nth 2 PT2)
          PT2 (list (car PT2) (cadr PT2))
    )
    (if (= "AECC_COGO_POINT" (cdr (assoc 0 ENTLIST)))
     (setq PT2 (vlax-get-property (vlax-ename->vla-object ENT) "Location")
           PT2 (vlax-variant-value PT2)
           ELEV2 (vlax-safearray-get-element PT2 2)
           PT2 (list (vlax-safearray-get-element PT2 0) (vlax-safearray-get-element PT2 1))
     )
    )
   )
  )
 )

 (if (and ELEV1 ELEV2)
  (progn
   (setq PTMID (list (/ (+ (car PT1) (car PT2)) 2.0)
                     (/ (+ (cadr PT1) (cadr PT2)) 2.0)
               )
   )
   (if (< ELEV1 ELEV2)
    (setq PT PT1)
    (setq PT PT2)
   )
   (setq GRADE (abs (/ (- ELEV2 ELEV1) (distance PT1 PT2))))
   (setvar "DIMZIN" 8)
   (if (< GRADE 0.10)
    (setq GRADE (strcat (rtos (* GRADE 100.0) 2 2) "%"))
    (setq GRADE (strcat (rtos (/ 1.0 GRADE) 2 2) ":1"))
   )
   (setvar "DIMZIN" DIMZIN)
   (if (setq ENT (RFL:INSERT RFL:PPSLOPEBLOCKNAME PTMID RFL:PPSLOPESCALE RFL:PPSLOPESCALE RFL:PPSLOPESCALE (angle PTMID PT)))
    (progn
     (setq ENTLIST (entget ENT))
     (if (= 1 (cdr (assoc 66 ENTLIST)))
      (progn
       (setq ENT2 (entnext ENT))
       (setq ENTLIST (entget ENT2))
       (while (/= "SEQEND" (cdr (assoc 0 ENTLIST)))
        (if (= "SLOPE" (cdr (assoc 2 ENTLIST)))
         (setq ENTLIST (subst (cons 1 GRADE) (assoc 1 ENTLIST) ENTLIST))
        )
        (entmod ENTLIST)
        (setq ENT2 (entnext ENT2))
        (setq ENTLIST (entget ENT2))
       )
       (entupd ENT)
      )
     )
    )
   )
  )
 )

 (command "._UCS" "P")
 (setvar "CMDECHO" CMDECHO)
 (setvar "ATTREQ" ATTREQ)
 (setvar "ANGBASE" ANGBASE)
 (setvar "ANGDIR" ANGDIR)
)
