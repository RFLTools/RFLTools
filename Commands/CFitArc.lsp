;
;
;   Program written by Robert Livingston, 00/05/29
;
;   FitArc fits a best-fit arc over a selected polyline (difference to BestArc is this holds endpoints)
;
;
(defun C:FITARC (/ ALIGNLIST ANGBASE ANGDIR BULGE BULGESTEP CMDECHO ENT ENT2 ENTLIST
                   P1 P2 P3 PLIST REP S SH SL SUMOS2 TAN)
 (setvar "CMDECHO" 0)
 (setq ANGBASE (getvar "ANGBASE"))
 (setvar "ANGBASE" 0.0)
 (setq ANGDIR (getvar "ANGDIR"))
 (setvar "ANGDIR" 0)

 (defun TAN (ANG)
  (/ (sin ANG) (cos ANG))
 )
 (defun SUMOS2 (/ C OS SOS)
  (setq C 1)
  (setq OS 0.0)
  (while (< C (- (length PLIST) 1))
   (setq SOS (RFL:STAOFF (nth C PLIST)))
   (if (= SOS nil)
    (progn
     (setq OS nil)
     (setq C (length PLIST))
    )
    (progn
     (setq OS (+ OS (expt (nth 1 SOS) 2)))
    )
   )
   (setq C (+ C 1))
  )
  (if (/= OS nil)
   (setq OS (/ OS (- (length PLIST) 2)))
  )
  (eval OS)
 )

 (defun DRAWARC (NODE / ANG1 ANG2 ENTLIST PC R)
  (setq PC (RFL:CENTER (nth 1 NODE) (nth 2 NODE) (nth 3 NODE)))
  (setq R (RFL:RADIUS (nth 1 NODE) (nth 2 NODE) (nth 3 NODE)))
  (if (> (last NODE) 0.0)
   (progn
    (setq ANG1 (angle PC (nth 1 NODE)))
    (setq ANG2 (angle PC (nth 2 NODE)))
   )
   (progn
    (setq ANG2 (angle PC (nth 1 NODE)))
    (setq ANG1 (angle PC (nth 2 NODE)))
   )
  )
  (setq ENTLIST (list (cons 0 "ARC")
                      (list 10 (nth 0 PC) (nth 1 PC) 0.0)
                      (cons 40 R)
                      (cons 50 ANG1)
                      (cons 51 ANG2)
                )
  )
  (command "._REDRAW")
  (entmake ENTLIST)
 )

 (setq ENT (car (entsel "\nSelect polyline :")))
 (setq ENT2 ENT)
 (setq ENTLIST (entget ENT))
 (setq PLIST nil)
 (if (= (cdr (assoc 0 ENTLIST)) "POLYLINE")
  (progn
   (setq ENT (entnext ENT))
   (setq ENTLIST (entget ENT))
   (while (/= (cdr (assoc 0 ENTLIST)) "SEQEND")
    (setq PLIST (append PLIST (list (list (nth 1 (assoc 10 ENTLIST)) (nth 2 (assoc 10 ENTLIST))))))
    (setq ENT (entnext ENT))
    (setq ENTLIST (entget ENT))
   )
  )
 )
 (if (= (cdr (assoc 0 ENTLIST)) "LWPOLYLINE")
  (progn
   (while (/= nil ENTLIST)
    (if (= (car (car ENTLIST)) 10)
     (setq PLIST (append PLIST (list (list (nth 1 (car ENTLIST)) (nth 2 (car ENTLIST))))))
    )
    (setq ENTLIST (cdr ENTLIST))
   )
  )
 )
 (if (= PLIST nil)
  (princ "\n***** NOT A POLYLINE *****")
  (progn
;   (setq BULGE 0.0)
   (setq P1 (car PLIST))
   (setq P2 (nth (/ (length PLIST) 2) PLIST))
   (setq P3 (last PLIST))
   (setq BULGE (/ (TAN (- (angle P2 P3) (angle P1 P2))) 4.0))
;   (setq BULGESTEP (/ (distance (car PLIST) (last PLIST)) 1000.0))
   (setq BULGESTEP (abs (/ BULGE 100.0)))
   (setq ALIGNLIST (list (list 0.0 (nth 0 PLIST) (last PLIST) BULGE)))
   (setq S (SUMOS2))
   (while (and (> BULGESTEP 0.000000005) (/= S nil))
    (setq ALIGNLIST (list (list 0.0 (nth 0 PLIST) (last PLIST) (+ BULGE BULGESTEP))))
    (setq SH (SUMOS2))
    (setq ALIGNLIST (list (list 0.0 (nth 0 PLIST) (last PLIST) (- BULGE BULGESTEP))))
    (setq SL (SUMOS2))
    (if (< SH SL)
     (progn
      (if (< SH S)
       (progn
        (setq BULGE (+ BULGE BULGESTEP))
        (setq S SH)
       )
       (progn
        (setq BULGESTEP (/ BULGESTEP 4.0))
       )
      )
     )
     (progn
      (if (< SL S)
       (progn
        (setq BULGE (- BULGE BULGESTEP))
        (setq S SL)
       )
       (progn
        (setq BULGESTEP (/ BULGESTEP 4.0))
       )
      )
     )
    )
   )
   (setq ALIGNLIST (list (list 0.0 (nth 0 PLIST) (last PLIST) BULGE)))
   (DRAWARC (nth 0 ALIGNLIST))
   (initget "Yes No")
   (setq REP (getkword "\nErase selected polyline (Yes/No) <Yes> :"))
   (if (or (= REP "Yes") (= REP nil))
    (command "._ERASE" ENT2 "")
   )
  )
 )

 (setvar "CMDECHO" 1)
 (setvar "ANGBASE" ANGBASE)
 (setvar "ANGDIR" ANGDIR)
)
