;
;
;    Program Written by Robert Livingston 99/08/10
;    PJOINALL is a utility for joining entities to a LWPolyline
;
;
(defun C:PJOINALL (/ ANG1 ANG2 C1 C2 CMDECHO ENT ENT1 ENT2 ENTLIST ENTLIST1 ENTLIST2 ENTSET ENTSET2 OSMODE
                     P1 P2 P3 P4 PC PINWHEEL PINWHEELCH PLINEENT PLINEENTLIST R TOL Z)
 (setq CMDECHO (getvar "CMDECHO"))
 (setvar "CMDECHO" 0)
 (setq OSMODE (getvar "OSMODE"))
 (setvar "OSMODE" 0)

 (defun PINWHEEL ()
  (if (= PINWHEELCH nil)
   (setq PINWHEELCH "|")
  )
  (setq PINWHEELCH (cond ((= PINWHEELCH "|") "/")
                         ((= PINWHEELCH "/") "-")
                         ((= PINWHEELCH "-") "\\")
                         ((= PINWHEELCH "\\") "|")))
  (princ "\r")
  (princ PINWHEELCH)
 )

 (setq ENTSET2 (ssget))
 (princ "\nFiltering out non-joinable entities ...")
 (setq ENTSET (ssadd))
 (setq C1 0)
 (while (< C1 (sslength ENTSET2))
  (setq ENT (ssname ENTSET2 C1))
  (setq ENTLIST (entget ENT))
  (if (or (= (cdr (assoc 0 ENTLIST)) "LINE")
          (= (cdr (assoc 0 ENTLIST)) "ARC")
          (= (cdr (assoc 0 ENTLIST)) "POLYLINE")
          (= (cdr (assoc 0 ENTLIST)) "LWPOLYLINE"))
   (progn
    (setq ENTSET (ssadd ENT ENTSET))
   )
  )
  (setq C1 (+ C1 1))
 )
 (if (/= ENTSET nil)
  (progn
   (setq TOL (getdist (strcat "\nEnter distance tolerance <" (rtos RFL:TOL) "> :")))
   (if (= TOL nil) (setq TOL RFL:TOL))
   (setq C1 0)
   (princ "\n")
   (while (< C1 (- (sslength ENTSET) 1))
    (setq ENT1 (ssname ENTSET C1))
    (setq ENTLIST1 (entget ENT1))
    (cond ((= (cdr (assoc 0 ENTLIST1)) "LINE")
           (progn
            (setq P1 (cdr (assoc 10 ENTLIST1)))
            (setq P2 (cdr (assoc 11 ENTLIST1)))
           )
          )
          ((= (cdr (assoc 0 ENTLIST1)) "ARC")
           (progn
            (setq PC (cdr (assoc 10 ENTLIST1)))
            (setq R (cdr (assoc 40 ENTLIST1)))
            (setq ANG1 (cdr (assoc 50 ENTLIST1)))
            (setq ANG2 (cdr (assoc 51 ENTLIST1)))
            (setq P1 (list (+ (nth 0 PC) (* R (cos ANG1)))
                           (+ (nth 1 PC) (* R (sin ANG1)))
                           (nth 2 PC)))
            (setq P2 (list (+ (nth 0 PC) (* R (cos ANG2)))
                           (+ (nth 1 PC) (* R (sin ANG2)))
                           (nth 2 PC)))
           )
          )
          ((= (cdr (assoc 0 ENTLIST1)) "POLYLINE")
           (progn
            (if (= (float (/ (cdr (assoc 70 ENTLIST1)) 2))
                   (/ (cdr (assoc 70 ENTLIST1)) 2.0))
             (progn
              (setq ENT (entnext ENT1))
              (setq ENTLIST (entget ENT))
              (setq P1 (cdr (assoc 10 ENTLIST)))
              (setq ENT (entnext ENT))
              (setq ENTLIST (entget ENT))
              (while (/= (cdr (assoc 0 ENTLIST)) "SEQEND")
               (setq P2 (cdr (assoc 10 ENTLIST)))
               (setq ENT (entnext ENT))
               (setq ENTLIST (entget ENT))
              )
             )
            )
           )
          )
          ((= (cdr (assoc 0 ENTLIST1)) "LWPOLYLINE")
           (progn
            (if (= (float (/ (cdr (assoc 70 ENTLIST1)) 2))
                   (/ (cdr (assoc 70 ENTLIST1)) 2.0))
             (progn
              (setq P1 (append (cdr (assoc 10 ENTLIST1)) (list (cdr (assoc 38 ENTLIST1)))))
              (setq P2 (append (cdr (assoc 10 (reverse ENTLIST1))) (list (cdr (assoc 38 ENTLIST1)))))
             )
            )
           )
          )
    )
    (setq C2 (+ C1 1))
    (while (< C2 (sslength ENTSET))
     (PINWHEEL)
     (setq ENT2 (ssname ENTSET C2))
     (setq ENTLIST2 (entget ENT2))
     (cond ((= (cdr (assoc 0 ENTLIST2)) "LINE")
            (progn
             (setq P3 (cdr (assoc 10 ENTLIST2)))
             (setq P4 (cdr (assoc 11 ENTLIST2)))
            )
           )
           ((= (cdr (assoc 0 ENTLIST2)) "ARC")
            (progn
             (setq PC (cdr (assoc 10 ENTLIST2)))
             (setq R (cdr (assoc 40 ENTLIST2)))
             (setq ANG1 (cdr (assoc 50 ENTLIST2)))
             (setq ANG2 (cdr (assoc 51 ENTLIST2)))
             (setq P3 (list (+ (nth 0 PC) (* R (cos ANG1)))
                            (+ (nth 1 PC) (* R (sin ANG1)))
                            (nth 2 PC)))
             (setq P4 (list (+ (nth 0 PC) (* R (cos ANG2)))
                            (+ (nth 1 PC) (* R (sin ANG2)))
                            (nth 2 PC)))
            )
           )
           ((= (cdr (assoc 0 ENTLIST2)) "POLYLINE")
            (progn
             (if (= (float (/ (cdr (assoc 70 ENTLIST2)) 2))
                    (/ (cdr (assoc 70 ENTLIST2)) 2.0))
              (progn
               (setq ENT (entnext ENT2))
               (setq ENTLIST (entget ENT))
               (setq P3 (cdr (assoc 10 ENTLIST)))
               (setq ENT (entnext ENT))
               (setq ENTLIST (entget ENT))
               (while (/= (cdr (assoc 0 ENTLIST)) "SEQEND")
                (setq P4 (cdr (assoc 10 ENTLIST)))
                (setq ENT (entnext ENT))
                (setq ENTLIST (entget ENT))
               )
              )
             )
            )
           )
           ((= (cdr (assoc 0 ENTLIST2)) "LWPOLYLINE")
            (progn
             (if (= (float (/ (cdr (assoc 70 ENTLIST2)) 2))
                    (/ (cdr (assoc 70 ENTLIST2)) 2.0))
              (progn
               (setq P3 (append (cdr (assoc 10 ENTLIST2)) (list (cdr (assoc 38 ENTLIST2)))))
               (setq P4 (append (cdr (assoc 10 (reverse ENTLIST2))) (list (cdr (assoc 38 ENTLIST2)))))
              )
             )
            )
           )
     )
     (if (or (< (distance (list (nth 0 P1) (nth 1 P1)) (list (nth 0 P3) (nth 1 P3))) TOL)
             (< (distance (list (nth 0 P1) (nth 1 P1)) (list (nth 0 P4) (nth 1 P4))) TOL)
             (< (distance (list (nth 0 P2) (nth 1 P2)) (list (nth 0 P3) (nth 1 P3))) TOL)
             (< (distance (list (nth 0 P2) (nth 1 P2)) (list (nth 0 P4) (nth 1 P4))) TOL))
      (progn
;       (if (/= ENT1 nil)
;        (progn
         (setq C2 (sslength ENTSET))
         (setq C1 -1)
         (setq ENTSET (ssdel ENT1 ENTSET))
       (setq Z (cond ((= (cdr (assoc 0 ENTLIST1)) "LINE")
                      (last (assoc 10 ENTLIST1))
                     )
                     ((= (cdr (assoc 0 ENTLIST1)) "ARC")
                      (last (assoc 10 ENTLIST1))
                     )
                     ((= (cdr (assoc 0 ENTLIST1)) "LWPOLYLINE")
                      (cdr (assoc 38 ENTLIST1))
                     )
                     ((= (cdr (assoc 0 ENTLIST1)) "POLYLINE")
                      (last (assoc 10 (entget (entnext ENT1))))
                     )))
       (setq ENT1 (RFL:ELEVFIX ENT1 Z))
         (setq ENTSET (RFL:PJOIN ENT1 ENTSET TOL))
;        )
;       )
      )
     )
     (setq C2 (+ C2 1))
    )
    (setq C1 (+ C1 1))
   )
  )
 )

 (setvar "CMDECHO" CMDECHO)
 (setvar "OSMODE" OSMODE)
 T
)
