;
;
;     Program written by Robert Livingston, 2018-10-26
;
;     C:AAARC attaches two tangents with two reverse arcs such that all entities are continuous and linear
;
;
(defun C:AAARC (/ ANG ANG1 ANG2 ANGD D ENT1 ENT2 ENTLIST1 ENTLIST2 FILLETRAD P P1 P11 P12 P2 P21 P22 PC1 PC2 PINT R R1 R2 TMP)
 (if (setq ENT1 (car (entsel "\nSelect first tangent : ")))
  (if (/= "LINE" (cdr (assoc 0 (setq ENTLIST1 (entget ENT1)))))
   (princ "\n*** ENTITY NOT A LINE ***")
   (progn
    (setq P11 (cdr (assoc 10 ENTLIST1))
          P11 (list (car P11) (cadr P11))
          P12 (cdr (assoc 11 ENTLIST1))
          P12 (list (car P12) (cadr P12))
    )
    (if (setq ENT2 (car (entsel "\nSelect second tangent : ")))
     (if (/= "LINE" (cdr (assoc 0 (setq ENTLIST2 (entget ENT2)))))
      (princ "\n*** ENTITY NOT A LINE ***")
      (progn
       (setq P21 (cdr (assoc 10 ENTLIST2))
             P21 (list (car P21) (cadr P21))
             P22 (cdr (assoc 11 ENTLIST2))
             P22 (list (car P22) (cadr P22))
       )
       (if (< (distance P11 P21) (distance P12 P21))
        (setq TMP P11 P11 P12 P12 TMP)
       )
       (setq P1 P12 ANG1 (angle P11 P12))
       (if (< (distance P22 P12) (distance P21 P12))
        (setq TMP P21 P21 P22 P22 TMP)
       )
       (setq P2 P21 ANG2 (angle P21 P22))
       (setq PINT (inters P11 P12 P21 P22 nil))
       (if (and PINT
                (< (distance P1 PINT) (distance P1 P2))
                (< (distance P2 PINT) (distance P1 P2))
           )
        (progn ; Single
         (princ "SINGLE\n")
         (setq D (min (distance P1 PINT) (distance P2 PINT)))
         (setq ANG (- ANG2 ANG1))
         (setq R (abs (/ D (RFL:TAN (/ ANG 2.0)))))
         (princ (strcat "R = " (rtos R) "\n"))
         (setq FILLETRAD (getvar "FILLETRAD"))
         (setvar "FILLETRAD" R)
         (command "._FILLET" ENT1 ENT2)
         (setvar "FILLETRAD" FILLETRAD)
        )
        (progn
         (setq P (list (/ (+ (car P1) (car P2)) 2.0) (/ (+ (cadr P1) (cadr P2)) 2.0)))
         (setq D (/ (distance P1 P2) 2.0))
         (setq ANGD (angle P1 P2))
         (if (< (abs (sin (- ANGD ANG1))) RFL:TOL)
          (entmake (list (cons 0 "LINE")
                         (cons 10 P1)
                         (cons 11 P2)
                   )
          )
          (if (> (sin (- ANGD ANG1)) 0.0)
           (progn ; Left
            (princ "LEFT\n")
            (setq ANG (abs (- ANGD ANG1)))
            (setq R1 (abs (/ (/ D 2.0) (sin ANG))))
            (setq PC1 (list (+ (car P1) (* R1 (cos (+ ANG1 (/ pi 2.0)))))
                            (+ (cadr P1) (* R1 (sin (+ ANG1 (/ pi 2.0)))))
                      )
            )
            (entmake (list (cons 0 "ARC")
                           (cons 10 PC1)
                           (cons 40 R1)
                           (cons 50 (angle PC1 P1))
                           (cons 51 (angle PC1 P))
                     )
            )
            (setq ANG (abs (- ANG2 ANGD)))
            (setq R2 (abs (/ (/ D 2.0) (sin ANG))))
            (setq PC2 (list (+ (car P2) (* R2 (cos (- ANG2 (/ pi 2.0)))))
                            (+ (cadr P2) (* R2 (sin (- ANG2 (/ pi 2.0)))))
                      )
            )
            (princ (strcat "R1 = " (rtos R1) ", R2 = " (rtos R2) "\n"))
            (entmake (list (cons 0 "ARC")
                           (cons 10 PC2)
                           (cons 40 R2)
                           (cons 50 (angle PC2 P2))
                           (cons 51 (angle PC2 P))
                     )
            )
           )
           (progn ; Right
            (princ "RIGHT\n")
            (setq ANG (abs (- ANGD ANG1)))
            (setq R1 (abs (/ (/ D 2.0) (sin ANG))))
            (setq PC1 (list (+ (car P1) (* R1 (cos (- ANG1 (/ pi 2.0)))))
                            (+ (cadr P1) (* R1 (sin (- ANG1 (/ pi 2.0)))))
                      )
            )
            (entmake (list (cons 0 "ARC")
                           (cons 10 PC1)
                           (cons 40 R1)
                           (cons 50 (angle PC1 P))
                           (cons 51 (angle PC1 P1))
                     )
            )
            (setq ANG (abs (- ANG2 ANGD)))
            (setq R2 (abs (/ (/ D 2.0) (sin ANG))))
            (setq PC2 (list (+ (car P2) (* R2 (cos (+ ANG2 (/ pi 2.0)))))
                            (+ (cadr P2) (* R2 (sin (+ ANG2 (/ pi 2.0)))))
                      )
            )
            (princ (strcat "R1 = " (rtos R1) ", R2 = " (rtos R2) "\n"))
            (entmake (list (cons 0 "ARC")
                           (cons 10 PC2)
                           (cons 40 R2)
                           (cons 50 (angle PC2 P))
                           (cons 51 (angle PC2 P2))
                     )
            )
           )
          )
         )
        )
       )
      )
     )
    )
   )
  )
 )
 T
)
