;
;
;   Program written by Robert Livingston, 99/12/03
;
;   ISOLATE is a routine for isolating the layer of a selected layer
;
;
(defun C:ISOLATE (/ CMDECHO CREATEDICTIONARY ENT ENT2 ENTLIST GETDICTIONARY
                    ISOLATEON ISOLATEOFF ISOLATELAYERLIST)
 (setq CMDECHO (getvar "CMDECHO"))
 (setvar "CMDECHO" 0)

 (defun ISOLATEON (/ TMP)
  (setq TMP ISOLATEOFFLIST)
  (command "._LAYER")
  (while (/= TMP nil)
   (command "ON" (car TMP))
   (setq TMP (cdr TMP))
  )
  (command "")
 )

 (defun ISOLATEOFF (/ TMP)
  (setq TMP ISOLATEOFFLIST)
  (command "._LAYER")
  (while (/= TMP nil)
   (command "OFF" (car TMP))
   (setq TMP (cdr TMP))
  )
  (command "")
 )

 (defun CREATEDICTIONARY (/ C DATALIST DICTIONARY NEWDICT XNAME)
  (setq DICTIONARY (list '(0 . "DICTIONARY") '(100 . "AcDbDictionary")))
  (setq XNAME (entmakex DICTIONARY))
  (setq NEWDICT (dictadd (namedobjdict) "RFL_ISOLATE_DICTIONARY" XNAME))
  (setq C 0)
  (setq DATALIST (list (cons 0 "XRECORD") (cons 100 "AcDbXrecord") (cons 1 ISOLATECLAYER)))
  (while (< C (length ISOLATEOFFLIST))
   (setq DATALIST (append DATALIST (list (cons 1 (nth C ISOLATEOFFLIST)))))
   (setq C (+ C 1))
  )
  (setq XNAME (entmakex DATALIST))
  (dictadd NEWDICT "DATA_RECORD_1" XNAME)
 )

 (defun GETDICTIONARY (/ ENT ENTLIST)
  (setq ENTLIST (dictsearch (namedobjdict) "RFL_ISOLATE_DICTIONARY"))
  (if (/= ENTLIST nil)
   (progn
    (setq ISOLATEOFFLIST nil)
    (setq ENT (cdr (assoc 350 ENTLIST)))
    (setq ENTLIST (entget ENT))
    (while (/= ENTLIST nil)
     (if (= (car (car ENTLIST)) 1)
      (progn
       (setq ISOLATEOFFLIST (append ISOLATEOFFLIST (list (cdr (car ENTLIST)))))
      )
     )
     (setq ENTLIST (cdr ENTLIST))
    )
    (setq ISOLATECLAYER (car ISOLATEOFFLIST))
    (setq ISOLATEOFFLIST (cdr ISOLATEOFFLIST))
    (dictremove (namedobjdict) "RFL_ISOLATE_DICTIONARY")
   )
  )
 )

 (GETDICTIONARY)
 (if (= ISOLATEONOFF nil) (setq ISOLATEONOFF 0))
 (if (/= ISOLATEOFFLIST nil) (setq ISOLATEONOFF 1))
 (if (= ISOLATEONOFF 0)
  (progn
   (setq ISOLATELAYERLIST nil)
   (setq ENT 1)
   (setq ENT2 nil)
   (while (/= nil ENT)
    (if (= ENT2 nil)
     (setq ENT2 (nentsel "\nSelect entity(s) to isolate (<return> when done) : "))
    )
    (if (listp ENT2)
     (if (> (length ENT2) 2)
      (setq ENT (car (last ENT2)) ENT2 (car ENT2))
      (setq ENT (car ENT2) ENT2 nil)
     )
     (setq ENT ENT2 ENT2 nil)
    )
    (if (/= ENT nil)
     (progn
      (setq ENTLIST (entget ENT))
      (setq ISOLATELAYERLIST (append ISOLATELAYERLIST (list (list (cdr (assoc 8 ENTLIST))))))
      (if (= (strcase (cdr (assoc 8 ENTLIST))) "DEFPOINTS")
       (setq ISOLATELAYERLIST (append ISOLATELAYERLIST (list (list "0"))))
      )
     )
    )
   )
   (if (/= ISOLATELAYERLIST nil)
    (progn
     (setq ISOLATECLAYER (getvar "CLAYER"))
     (setvar "CLAYER" (car (car ISOLATELAYERLIST)))
     (setq ISOLATEOFFLIST nil)
     (setq ENTLIST (tblnext "LAYER" 1))
     (while (/= ENTLIST nil)
      (if (and (= (assoc (cdr (assoc 2 ENTLIST)) ISOLATELAYERLIST) nil)
               (> (cdr (assoc 62 ENTLIST)) 0)
               (= (float (/ (cdr (assoc 70 ENTLIST)) 2))
                  (/ (cdr (assoc 70 ENTLIST)) 2.0)
               )
          )
       (progn
        (setq ISOLATEOFFLIST (append ISOLATEOFFLIST (list (cdr (assoc 2 ENTLIST)))))
       )
      )
      (setq ENTLIST (tblnext "LAYER"))
     )
     (CREATEDICTIONARY)
     (ISOLATEOFF)
     (setq ISOLATEONOFF 1)
    )
   )
  )
  (progn
   (ISOLATEON)
   (if (/= nil (tblsearch "LAYER" ISOLATECLAYER))
    (setvar "CLAYER" ISOLATECLAYER)
   )
   (setq ISOLATEOFFLIST nil)
   (setq ISOLATECLAYER nil)
   (setq ISOLATEONOFF 0)
   (setq ISOLATELAYERLIST nil)
  )
 )

 (setvar "CMDECHO" CMDECHO)
)
