;
;
;     Program written by Robert Livingston
;
;     C:TXT2PLINE converts text to polyline using the TXTEXP Express tool.
;
;
(defun C:TXT2PLINE (/ A C C2 COLOR ENT ENTLIST ENTSET ENTSETTEXT ENTSETTMP LAYER PBOX P PM1 PM2 P1 P2 P3 P4 TMPFIL)
 (command "._UNDO" "M")
 (setq ENTSETTEXT (ssadd))
 (setq C 0)
 (setq ENTSET (ssget))
 (while (< C (sslength ENTSET))
  (setq ENT (ssname ENTSET C))
  (setq ENTLIST (entget ENT))
  (if (= (cdr (assoc 0 ENTLIST)) "TEXT")
   (ssadd ENT ENTSETTEXT)
  )
  (if (= (cdr (assoc 0 ENTLIST)) "MTEXT")
   (progn
    (command "._EXPLODE" ENT)
    (setq ENTSETTMP (ssget "P"))
    (setq C2 0)
    (while (< C2 (sslength ENTSETTMP))
     (ssadd (ssname ENTSETTMP C2) ENTSETTEXT)
     (setq C2 (1+ C2))
    )
   )
  )
  (setq C (1+ C))
 )
 (setq C 0)
 (while (< C (sslength ENTSETTEXT))
  (setq ENT (ssname ENTSETTEXT C))
  (setq ENTLIST (entget ENT))
  (if (or (= (cdr (assoc 0 ENTLIST)) "TEXT")
          (= (cdr (assoc 0 ENTLIST)) "MTEXT")
      )
   (progn
    (setq LAYER (cdr (assoc 8 ENTLIST)))
    (setq COLOR (cdr (assoc 62 ENTLIST)))
    (setq PBOX (textbox ENTLIST))
;    (setq PBOX (acet-geom-textbox ENTLIST 0))
    (setq A (cdr (assoc 50 ENTLIST)))
    (setq P (cdr (assoc 10 ENTLIST)))
    (setq P1 (list (+ (car P) (* (car (car PBOX)) (cos A)) (* -1.0 (cadr (car PBOX)) (sin A)))
                   (+ (cadr P) (* (car (car PBOX)) (sin A)) (* (cadr (car PBOX)) (cos A)))
             )
    )
    (setq P2 (list (+ (car P) (* (car (cadr PBOX)) (cos A)) (* -1.0 (cadr (car PBOX)) (sin A)))
                   (+ (cadr P) (* (car (cadr PBOX)) (sin A)) (* (cadr (car PBOX)) (cos A)))
             )
    )
    (setq P3 (list (+ (car P) (* (car (cadr PBOX)) (cos A)) (* -1.0 (cadr (cadr PBOX)) (sin A)))
                   (+ (cadr P) (* (car (cadr PBOX)) (sin A)) (* (cadr (cadr PBOX)) (cos A)))
             )
    )
    (setq P4 (list (+ (car P) (* (car (car PBOX)) (cos A)) (* -1.0 (cadr (cadr PBOX)) (sin A)))
                   (+ (cadr P) (* (car (car PBOX)) (sin A)) (* (cadr (cadr PBOX)) (cos A)))
             )
    )
;    (setq P1 (car PBOX)
;          P2 (cadr PBOX)
;          P3 (caddr PBOX)
;          P4 (cadddr PBOX)
;    )
    (setq PM1 (list (min (car P1) (car P2) (car P3) (car P4)) (- (min (cadr P1) (cadr P2) (cadr P3) (cadr P4)) (acet-geom-pixel-unit))))
    (setq PM2 (list (max (car P1) (car P2) (car P3) (car P4)) (+ (max (cadr P1) (cadr P2) (cadr P3) (cadr P4)) (acet-geom-pixel-unit))))
    
    (command "._ZOOM" "W" PM1 PM2)
    (setq TMPFIL (strcat (getvar "tempprefix") "txtexp.wmf"))

    (command "_.WMFOUT" TMPFIL ENT "")
    
    (if (findfile TMPFIL)
     (progn
      (command "_.ERASE" ENT "")
      (setq SS (acet-wmfin TMPFIL))
      (command "._CHANGE" SS "" "P" "C" (if COLOR COLOR "BYLAYER") "LA" LAYER "")
     )
    )

    (command "._ZOOM" "P")
   )
  )
  
  (setq C (1+ C))
 )
 T
)
