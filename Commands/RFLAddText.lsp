;
;
;     Program written by Robert Livingston, 2022-02-01
;
;     RFL:ADDTEXT and RFL:ADDMTEXT are routins for creating text entities
;
;
(defun RFL:ADDTEXT (P AL H TXT / ENTOB MSPACE)
 (vl-load-com)
 (if (= (length P) 2) (setq P (list (car P) (cadr P) 0.0)))
 (setq AL (strcase AL))
 (setq MSPACE (vla-get-modelspace (vla-get-activedocument (vlax-get-acad-object))))
 (if (setq ENTOB (vla-addText MSPACE TXT (vlax-3d-point P) H))
  (progn
   (cond ((= AL "C")
          (vla-put-Alignment ENTOB acAlignmentCenter)
          (vla-put-TextAlignmentPoint ENTOB (vlax-3d-point P))
         )
         ((= AL "R")
          (vla-put-Alignment ENTOB acAlignmentRight)
          (vla-put-TextAlignmentPoint ENTOB (vlax-3d-point P))
         )
         ((= AL "A")
          (vla-put-Alignment ENTOB acAlignmentAligned)
          (vla-put-TextAlignmentPoint ENTOB (vlax-3d-point P))
         )
         ((= AL "M")
          (vla-put-Alignment ENTOB acAlignmentMiddle)
          (vla-put-TextAlignmentPoint ENTOB (vlax-3d-point P))
         )
         ((= AL "F")
          (vla-put-Alignment ENTOB acAlignmentFit)
          (vla-put-TextAlignmentPoint ENTOB (vlax-3d-point P))
         )
         ((= AL "TL")
          (vla-put-Alignment ENTOB acAlignmentTopLeft)
          (vla-put-TextAlignmentPoint ENTOB (vlax-3d-point P))
         )
         ((= AL "TR")
          (vla-put-Alignment ENTOB acAlignmentTopRight)
          (vla-put-TextAlignmentPoint ENTOB (vlax-3d-point P))
         )
         ((= AL "TC")
          (vla-put-Alignment ENTOB acAlignmentTopCenter)
          (vla-put-TextAlignmentPoint ENTOB (vlax-3d-point P))
         )
         ((= AL "ML")
          (vla-put-Alignment ENTOB acAlignmentMiddleLeft)
          (vla-put-TextAlignmentPoint ENTOB (vlax-3d-point P))
         )
         ((= AL "MR")
          (vla-put-Alignment ENTOB acAlignmentMiddleRight)
          (vla-put-TextAlignmentPoint ENTOB (vlax-3d-point P))
         )
         ((= AL "MC")
          (vla-put-Alignment ENTOB acAlignmentMiddleCenter)
          (vla-put-TextAlignmentPoint ENTOB (vlax-3d-point P))
         )
         ((= AL "BL")
          (vla-put-Alignment ENTOB acAlignmentBottomLeft)
          (vla-put-TextAlignmentPoint ENTOB (vlax-3d-point P))
         )
         ((= AL "BR")
          (vla-put-Alignment ENTOB acAlignmentBottomRight)
          (vla-put-TextAlignmentPoint ENTOB (vlax-3d-point P))
         )
         ((= AL "BC")
          (vla-put-Alignment ENTOB acAlignmentBottomCenter)
          (vla-put-TextAlignmentPoint ENTOB (vlax-3d-point P))
         )
   )
   (vlax-vla-object->ename ENTOB)
  )
  nil
 )
)
