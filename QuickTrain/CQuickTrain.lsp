;
;
;     Program written by Robert Livingston, 2013-05-01
;
;     C:QUICKTRAIN models a train along a track alignment
;
;
(defun C:QUICKTRAIN (/ *error* ANGBASE ANGDIR ATTREQ CA CHECKTRUCKP2 CMDECHO ENT ENTC ENTT1 ENTT2 ENTLIST ENTLISTC ENTLISTC2 ENTLISTT1 ENTLISTT2 ENTLISTT3 ENTSET NAMECAR NAMETRUCK1 NAMETRUCK2 ORTHOMODE OSMODE P REP STA STEP STR TMP TMP2 TRACETOGGLE TRACEPOINT)
 (command "._UNDO" "M")
 (setq ATTREQ (getvar "ATTREQ"))
 (setvar "ATTREQ" 0)
 (setq ANGBASE (getvar "ANGBASE"))
 (setvar "ANGBASE" 0.0)
 (setq ANGDIR (getvar "ANGDIR"))
 (setvar "ANGDIR" 1)
 (setq CMDECHO (getvar "CMDECHO"))
 (setvar "CMDECHO" 0)
 (setq OSMODE (getvar "OSMODE"))
 (setvar "OSMODE" 0)
 (setq ORTHOMODE (getvar "ORTHOMODE"))
 (setvar "ORTHOMODE" 0)

 (defun CHECKTRUCKP2 (ENT / ENT2 ENTLIST FLAG)
  (setq FLAG nil)
  (setq ENT2 (entnext ENT))
  (setq ENTLIST (entget ENT2))
  (while (= "ATTRIB" (cdr (assoc 0 ENTLIST)))
   (if (= "DX2" (cdr (assoc 2 ENTLIST))) (setq FLAG T))
   (setq ENT2 (entnext ENT2))
   (setq ENTLIST (entget ENT2))
  )
  (eval FLAG)
 )
 
 (defun *error* (msg)
  (if (/= nil ENTSET)
   (progn
    (entmod ENTLISTC)
    (entupd (ssname ENTSET 0))
    (entmod ENTLISTT1)
    (entupd (ssname ENTSET 1))
    (entmod ENTLISTT2)
    (entupd (ssname ENTSET 2))
    (if (/= nil ENTLISTC2)
     (progn
      (entmod ENTLISTC2)
      (entupd (ssname ENTSET 3))
     )
    )
    (if (/= nil ENTLISTT3)
     (progn
      (entmod ENTLISTT3)
      (entupd (ssname ENTSET 4))
     )
    )
   )
  )
  (setvar "ATTREQ" ATTREQ)
  (setvar "ANGBASE" ANGBASE)
  (setvar "ANGDIR" ANGDIR)
  (setvar "CMDECHO" CMDECHO)
  (setvar "OSMODE" OSMODE)
  (setvar "ORTHOMODE" ORTHOMODE)
  (print msg)
 )

 (if (= nil RFL:ALIGNLIST)
  (princ "\n*** Alignment Not Defined ***")
  (progn
   (if (/= nil (setq ENTC (car (entsel "\nSelect Rail Car : "))))
    (progn
     (setq ENTLISTC (entget ENTC))
     (if (/= nil (setq ENTT1 (car (entsel "\nSelect Rear Truck : "))))
      (progn
       (setq ENTLISTT1 (entget ENTT1))
       (if (/= nil (setq ENTT2 (car (entsel "\nSelect Front (or Middle) Truck : "))))
        (progn
         (setq ENTLISTT2 (entget ENTT2))
         (setq P T)
         (setq ENTSET (ssadd))
         (setq ENTSET (ssadd ENTC ENTSET))
         (setq ENTSET (ssadd ENTT1 ENTSET))
         (setq ENTSET (ssadd ENTT2 ENTSET))
         (if (CHECKTRUCKP2 ENTT2)
          (progn
           (setq ENTLISTC2 nil ENTLISTT3 nil)
           (if (/= nil (setq ENTC (car (entsel "\nSelect Second Rail Car : "))))
            (progn
             (setq ENTLISTC2 (entget ENTC))
             (setq ENTSET (ssadd ENTC ENTSET))
             (if (/= nil (setq ENTT2 (car (entsel "\nSelect Front Truck : "))))
              (progn
               (setq ENTLISTT3 (entget ENTT2))
               (setq ENTSET (ssadd ENTT2 ENTSET))
              )
             )
            )
           )
          )
         )
         (setq STA nil)
         (while (= nil STA)
          (setq P (getpoint "\nPick point along alignment : "))
          (setq STA (car (RFL:STAOFF P)))
          (if (= nil STA)
           (princ "\nPoint not along alignment - please try again.\n")
           (progn
            (setq CA (RFL:UPDATETRAIN STA ENTSET))
            (if (= nil CA)
             (progn
              (princ "\nCannot place train at this location - please try again.\n")
              (setq STA nil)
             )
            )
           )
          )
         )
         (if (/= nil ENTSET)
          (progn
           (setq TRACETOGGLE nil)
           (setq INC 1.0)
           (setq REP "Inc")
           (if TRACETOGGLE
            (progn
             (initget "Inc Trace eXit")
             (setq STR (strcat "\nInc (" (rtos INC 2 3) "), Trace off, eXit <" REP "> : "))
            )
            (progn
             (initget "Copy Point Sta Inc sEtinc Trace eXit")
             (setq STR (strcat "\nCopy, Point, Sta (" (rtos STA 2 2) "), Inc (" (rtos INC 2 3) "), sEtinc, Trace on, eXit <" REP "> : "))
            )
           )
           (while (/= "eXit" (setq TMP (getkword STR)))
            (if (/= nil TMP) (setq REP TMP))
            (cond ((= REP "Copy")
                   (progn
                    (command "._COPY" ENTSET "" (list 0.0 0.0) (list 0.0 0.0))
                    (setq REP "Inc")
                   )
                  )
                  ((= REP "Point")
                   (progn
                    (setq TMP STA)
                    (while (= nil (setq STA (car (RFL:STAOFF (getpoint "\nSelect Point : "))))))
                    (if (= nil (setq TMP2 (RFL:UPDATETRAIN STA ENTSET)))
                     (setq STA TMP)
                     (setq CA TMP2)
                    )
                    (setq REP "Inc")
                   )
                  )
                  ((= REP "Sta")
                   (progn
                    (setq TMP STA)
                    (while (= nil (setq STA (getreal "\nEnter Station : "))))
                    (if (= nil (setq TMP2 (RFL:UPDATETRAIN STA ENTSET)))
                     (setq STA TMP)
                     (setq CA TMP2)
                    )
                    (setq REP "Inc")
                   )
                  )
                  ((= REP "Inc")
                   (progn
                    (setq STA (+ STA INC))
                    (if (= nil (setq TMP2 (RFL:UPDATETRAIN STA ENTSET)))
                     (setq STA (- STA INC))
                     (setq CA TMP2)
                    )
                   )
                  )
                  ((= REP "sEtinc")
                   (progn
                    (while (= nil (setq INC (getreal "\nEnter new step size : "))))
                    (setq REP "Inc")
                   )
                  )
                  ((= REP "Trace")
                   (progn
                    (if TRACETOGGLE
                     (progn
                      (setq TRACETOGGLE nil)
                     )
                     (progn
                      (setq TRACETOGGLE T)
                      (setq XXX (getpoint "\nPick trace point : "))
                      (setq XXX2 CA)
                     )
                    )
                    (setq REP "Inc")
                   )
                  )
            )
            (if TRACETOGGLE
             (progn
              (initget "Inc Trace eXit")
              (setq STR (strcat "\nInc (" (rtos INC 2 3) "), Trace off, eXit <" REP "> : "))
             )
             (progn
              (initget "Copy Point Sta Inc sEtinc Trace eXit")
              (setq STR (strcat "\nCopy, Point, Sta (" (rtos STA 2 2) "), Inc (" (rtos INC 2 3) "), sEtinc, Trace on, eXit <" REP "> : "))
             )
            )
           )
           (entmod ENTLISTC)
           (entupd (ssname ENTSET 0))
           (entmod ENTLISTT1)
           (entupd (ssname ENTSET 1))
           (entmod ENTLISTT2)
           (entupd (ssname ENTSET 2))
           (if (/= nil ENTLISTC2)
            (progn
             (entmod ENTLISTC2)
             (entupd (ssname ENTSET 3))
            )
           )
           (if (/= nil ENTLISTT3)
            (progn
             (entmod ENTLISTT3)
             (entupd (ssname ENTSET 4))
            )
           )
          )
         )
        )
       )
      )
     )
    )
   )      
  )
 )
 
 (setvar "ATTREQ" ATTREQ)
 (setvar "ANGBASE" ANGBASE)
 (setvar "ANGDIR" ANGDIR)
 (setvar "CMDECHO" CMDECHO)
 (setvar "OSMODE" OSMODE)
 (setvar "ORTHOMODE" ORTHOMODE)
)
