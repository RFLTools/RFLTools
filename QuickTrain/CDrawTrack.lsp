;
;
;     Program written by Robert Livingston, 2013-06-05
;
;     DRAWTRACK is a utility for drawing train tracks at elevation and super
;
;
(defun C:DRAWTRACK (/ *error* CMDECHO E GAUGE REP STA STAEND STASTART ORTHOMODE OS OSMODE STEP Z)
 (command "._UNDO" "M")
 
 (setq ANGBASE (getvar "ANGBASE"))
 (setvar "ANGBASE" 0.0)
 (setq ANGDIR (getvar "ANGDIR"))
 (setvar "ANGDIR" 0)
 (setq CMDECHO (getvar "CMDECHO"))
 (setvar "CMDECHO" 0)
 (setq OSMODE (getvar "OSMODE"))
 (setvar "OSMODE" 0)
 (setq ORTHOMODE (getvar "ORTHOMODE"))
 (setvar "ORTHOMODE" 0)

 (defun *error* (msg)
  (setvar "CMDECHO" CMDECHO)
  (setq *error* nil)
  (setvar "ANGBASE" ANGBASE)
  (setvar "ANGDIR" ANGDIR)
  (setvar "CMDECHO" CMDECHO)
  (setvar "OSMODE" OSMODE)
  (setvar "ORTHOMODE" ORTHOMODE)
  (princ msg)
 )

 (setq STASTART (caar RFL:ALIGNLIST))
 (if (= nil STASTART)
  (princ "\nNo alignment defined!")
  (progn
   (setq STAEND (+ (RFL:GETALIGNLENGTH)(caar RFL:ALIGNLIST)))
   (if (/= nil RFL:PVILIST)
    (progn
     (if (> (caar RFL:PVILIST) STASTART) (setq STASTART (caar RFL:PVILIST)))
     (if (< (car (last RFL:PVILIST)) STAEND) (setq STAEND (car (last RFL:PVILIST))))
    )
   )
   (if (/= nil RFL:SUPERLIST)
    (progn
     (if (> (caar RFL:SUPERLIST) STASTART) (setq STASTART (caar RFL:SUPERLIST)))
     (if (< (car (last RFL:SUPERLIST)) STAEND) (setq STAEND (car (last RFL:SUPERLIST))))
    )
   )
   (setq REP nil)
   (while (= nil REP)
    (setq REP (getreal (strcat "\nEnter start station <" (rtos STASTART) "> : ")))
    (if (= nil REP)
     (setq REP T)
     (if (< REP STASTART)
      (setq REP nil)
      (setq STASTART REP)
     )
    )
   )
   (setq REP nil)
   (while (= nil REP)
    (setq REP (getreal (strcat "\nEnter end station <" (rtos STAEND) "> : ")))
    (if (= nil REP)
     (setq REP T)
     (if (> REP STAEND)
      (setq REP nil)
      (setq STAEND REP)
     )
    )
   )
   (setq STEP (getdist "\nEnter step size <10.000> : "))
   (if (= nil STEP) (setq STEP 10.0))
   (setq GAUGE (getdist "\nEnter track gauge <1.435> : "))
   (if (= nil GAUGE) (setq GAUGE 1.435))
   (setq STA STASTART)
   (command "._3DPOLY")
   (while (<= STA STAEND)
    (princ "\r                    \r")
    (princ (rtos STA 2 1))
    (setq Z (RFL:ELEVATION STA))
    (if (= nil Z) (setq Z 0.0))
    (setq E (RFL:SUPER STA))
    (if (= nil E) (setq E (list 0.0 0.0)))
    (setq OS (/ (sqrt (- (expt GAUGE 2) (expt (/ (abs (- (car E) (cadr E))) 1000.0) 2))) 2.0))
    (setq Z (+ Z (/ (car E) 1000.0)))
    (command (append (RFL:XY (list STA (* -1.0 OS))) (list Z)))
    (setq STA (+ STA STEP))
   )
   (command "")
   (setq STA STASTART)
   (command "._3DPOLY")
   (while (<= STA STAEND)
    (princ "\r                    \r")
    (princ (rtos STA 2 1))
    (setq Z (RFL:ELEVATION STA))
    (if (= nil Z) (setq Z 0.0))
    (setq E (RFL:SUPER STA))
    (if (= nil E) (setq E (list 0.0 0.0)))
    (setq OS (/ (sqrt (- (expt GAUGE 2) (expt (/ (abs (- (car E) (cadr E))) 1000.0) 2))) 2.0))
    (setq Z (+ Z (/ (cadr E) 1000.0)))
    (command (append (RFL:XY (list STA OS)) (list Z)))
    (setq STA (+ STA STEP))
   )
   (command "")
  )
 )

 (setvar "ANGBASE" ANGBASE)
 (setvar "ANGDIR" ANGDIR)
 (setvar "CMDECHO" CMDECHO)
 (setvar "OSMODE" OSMODE)
 (setvar "ORTHOMODE" ORTHOMODE)
 T
)
