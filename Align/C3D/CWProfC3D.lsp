;
;
;     Program written by Robert Livingston, 2016-11-02
;
;     WPROFC3D writes the current RFL profile as the design centerline of a selected C3D alignment
;
;
(defun C:WPROFC3D (/ C CMAX FLAG GETOBAECC LANDPROFILESTYLENAME NAME NODE OALIGNMENT OALIGNMENTS
                     OCIVILAPP ODOCUMENT OLANDPROFILESTYLES OPROFILE OPROFILES OPVIS PROFNAME TOL)
 (setq TOL 0.000001)
 (defun GETOBAECC (/ *acad* ACADACTIVEDOCUMENT ACADPROD ACADVER C3DOBJECT C3DDOC C3DSURFS C CMAX C3DSURF)
  (princ "\n")
  (setq ACADPROD (vlax-product-key))
  (setq ACADVER (RFL:ACADVER))
  (setq ACADPROD (strcat "AeccXUiLand.AeccApplication." ACADVER))
  (setq *acad* (vlax-get-acad-object))
  (vla-getinterfaceobject *acad* ACADPROD)
 )

 (if (/= nil RFL:PVILIST)
  (progn
   (setq OCIVILAPP (GETOBAECC))
   (if (= nil OCIVILAPP)
    (alert "C3D not loaded!")
    (progn
     (setq ODOCUMENT (vlax-get-property OCIVILAPP "ActiveDocument"))
     (if (= nil ODOCUMENT)
      (alert "Error getting Document!")
      (progn
       (setq OALIGNMENTS (vlax-get-property ODOCUMENT "AlignmentsSiteless"))
       (if (= nil OALIGNMENTS)
        (alert "Error getting Alignments!")
        (progn
         (textscr)
         (setq CMAX (vlax-get-property OALIGNMENTS "Count"))
         (setq C 0)
         (while (< C CMAX)
          (princ (strcat (itoa (+ C 1)) " : " (vlax-get-property (vlax-invoke-method OALIGNMENTS "Item" C) "Name") "\n"))
          (setq C (+ C 1))
         )
         (setq C 0)
         (while (or (< C 1) (> C CMAX))
          (setq C (getint (strcat "Select Alignment < 1 to " (itoa CMAX) " > : ")))
         )
         (setq C (- C 1))
         (setq OALIGNMENT (vlax-invoke-method OALIGNMENTS "Item" C))
         (setq NAME (vlax-get-property OALIGNMENT "Name"))
         (princ "\n")
         (setq OPROFILES (vlax-get-property OALIGNMENT "Profiles"))
         (setq PROFNAME (getstring T "\nEnter new profile name : "))
         (setq FLAG nil)
         (setq CMAX (vlax-get-property OPROFILES "Count"))
         (setq C 0)
         (while (< C CMAX)
          (if (= (strcase PROFNAME) (strcase (vlax-get-property (vlax-invoke-method OPROFILES "Item" C) "Name")))
           (setq FLAG T)
          )
          (setq C (1+ C))
         )
         (if FLAG
          (princ "\nProfile already exists for this alignment - you must enter a new name.")
          (progn
           (setq OLANDPROFILESTYLES (vlax-get-property ODOCUMENT "LandProfileStyles"))
           (if (= nil OLANDPROFILESTYLES)
            (alert "Error getting Profile Styles!")
            (progn
             (setq CMAX (vlax-get-property OLANDPROFILESTYLES "Count"))
             (setq C 0)
             (while (< C CMAX)
              (princ (strcat (itoa (+ C 1)) " : " (vlax-get-property (vlax-get-property OLANDPROFILESTYLES "Item" C) "Name") "\n"))
              (setq C (+ C 1))
             )
             (setq C 0)
             (while (or (< C 1) (> C CMAX))
              (setq C (getint (strcat "Select Profile Style < 1 to " (itoa CMAX) " > : ")))
             )
             (setq C (- C 1))
             (setq LANDPROFILESTYLENAME (vlax-get-property (vlax-get-property OLANDPROFILESTYLES "Item" C) "Name"))
             (princ "\n")
             (setq OPROFILE (vlax-invoke-method OPROFILES "Add" PROFNAME 2 LANDPROFILESTYLENAME))
             (setq OPVIS (vlax-get-property OPROFILE "PVIs"))
             (setq NODE (car RFL:PVILIST))
             (vlax-invoke-method OPVIS "Add" (nth 0 NODE) (nth 1 NODE) 1)
             (setq NODE (last RFL:PVILIST))
             (vlax-invoke-method OPVIS "Add" (nth 0 NODE) (nth 1 NODE) 1)
             (setq C 1)
             (while (< C (- (length RFL:PVILIST) 1))
              (setq NODE (nth C RFL:PVILIST))
              (if (< (nth 3 NODE) TOL)
               (vlax-invoke-method OPVIS "Add" (nth 0 NODE) (nth 1 NODE) 1)
               (vlax-invoke-method OPVIS "Add" (nth 0 NODE) (nth 1 NODE) 3 (nth 3 NODE))
              )
              (setq C (+ C 1))
             )
            )
           )
          )
         )
        )
       )
      )
     )
    )
   )
  )
 )
)
