;
;
;     Program written by Robert Livingston 2014-11-24
;
;     DRAPEALIGN drapes a RFL Alignment
;
;     Revised 2026-10-20 (Hermes):
;       * prints a drape summary before returning - number of vertices added and
;         the minimum / maximum elevation of the resulting 3D polyline,
;       * OGLIST added to the local list (it was leaking as a global, so a run that
;         failed at the surface stage would have reported the previous run's points).
;
(defun C:DRAPEALIGN (/ *error* ALSAVE ANG ANGBASE ANGDIR ATOTAL C CMAX CMDECHO EMIN EMAX L LSTEP NODE NVERT OBSURFACE OGLIST OSMODE ORTHOMODE OSTOL P1 P2 R TMP TMPLIST Z)
 (setq CMDECHO (getvar "CMDECHO"))
 (setvar "CMDECHO" 0)
 (setq ANGBASE (getvar "ANGBASE"))
 (setvar "ANGBASE" 0)
 (setq ANGDIR (getvar "ANGDIR"))
 (setvar "ANGDIR" 0)
 (setq OSMODE (getvar "OSMODE"))
 (setvar "OSMODE" 0)
 (setq ORTHOMODE (getvar "ORTHOMODE"))
 (setvar "ORTHOMODE" 0)

 (setq ALSAVE RFL:ALIGNLIST)
 
 (setq OSTOL 0.1)
 
 (defun *error* (msg)
  (setvar "CMDECHO" CMDECHO)
  (setvar "ANGBASE" ANGBASE)
  (setvar "ANGDIR" ANGDIR)
  (setvar "OSMODE" OSMODE)
  (setvar "ORTHOMODE" ORTHOMODE)
  (setq RFL:ALIGNLIST ALSAVE)
  ;(setq *error* nil)
  (print msg)
 )

 (command ".UNDO" "M")

 (if (= nil RFL:ALIGNLIST)
  (princ "\n*** Alignment not defined ***")
  (progn
   (setq OBSURFACE (RFL:GETC3DSURFACE))
   (if (= nil OBSURFACE)
    (princ "\n*** Error getting C3D Surface ***")
    (progn
     (setq OGLIST nil)
     (foreach NODE ALSAVE
      (progn
       (if (listp (last NODE))
        (progn ; SPIRAL
         (setq R (RFL:GETSPIRALR2 (nth 0 (last NODE)) (nth 1 (last NODE)) (nth 2 (last NODE))))
         (setq L (RFL:GETSPIRALLS2 (nth 0 (last NODE)) (nth 1 (last NODE)) (nth 2 (last NODE))))
         (if (not (listp (last (last NODE))))
          (setq L (- L (last (last NODE))))
         )
         (setq ANG (atan (/ (sqrt (- (* 2.0 R OSTOL) (* OSTOL OSTOL))) (- R OSTOL))))
         (setq LSTEP (* 2.0 R ANG))
         (setq CMAX (+ 1 (fix (/ L LSTEP))))
         (setq LSTEP (/ L CMAX))
         (setq RFL:ALIGNLIST (list (list 0.0 (nth 1 NODE) (nth 2 NODE) (nth 3 NODE))))
         (setq P1 (nth 1 NODE))
         (setq C 1)
         (while (< C CMAX)
          (setq P2 (RFL:XY (list (* C LSTEP) 0.0)))
          (if (/= nil (setq TMPLIST (RFL:GETSURFACELINE P1 P2 OBSURFACE)))
           (if (= nil OGLIST)
            (setq OGLIST (append OGLIST TMPLIST))
            (setq OGLIST (append OGLIST (cdr TMPLIST)))
           )
          )
          (setq C (+ C 1))
          (setq P1 P2)
         )
         (setq P2 (nth 2 NODE))
         (if (/= nil (setq TMPLIST (RFL:GETSURFACELINE P1 P2 OBSURFACE)))
          (if (= nil OGLIST)
           (setq OGLIST (append OGLIST TMPLIST))
           (setq OGLIST (append OGLIST (cdr TMPLIST)))
          )
         )
        )
        (if (< (abs (last NODE)) RFL:TOL)
         (progn ; LINE
          (setq P1 (nth 1 NODE))
          (setq P2 (nth 2 NODE))
          (if (/= nil (setq TMPLIST (RFL:GETSURFACELINE P1 P2 OBSURFACE)))
           (if (= nil OGLIST)
            (setq OGLIST (append OGLIST TMPLIST))
            (setq OGLIST (append OGLIST (cdr TMPLIST)))
           )
          )
         )
         (progn ; ARC
          (setq R (RFL:RADIUS (nth 1 NODE) (nth 2 NODE) (nth 3 NODE)))
          (setq ATOTAL (* 4 (atan (abs (nth 3 NODE)))))
          (setq L (* R ATOTAL))
          (setq ANG (atan (/ (sqrt (- (* 2.0 R OSTOL) (* OSTOL OSTOL))) (- R OSTOL))))
          (setq LSTEP (* 2.0 R ANG))
          (setq CMAX (+ 1 (fix (/ L LSTEP))))
          (setq LSTEP (/ L CMAX))
          (setq RFL:ALIGNLIST (list (list 0.0 (nth 1 NODE) (nth 2 NODE) (nth 3 NODE))))
          (setq P1 (nth 1 NODE))
          (setq C 1)
          (while (< C CMAX)
           (setq P2 (RFL:XY (list (* C LSTEP) 0.0)))
           (if (/= nil (setq TMPLIST (RFL:GETSURFACELINE P1 P2 OBSURFACE)))
            (if (= nil OGLIST)
             (setq OGLIST (append OGLIST TMPLIST))
             (setq OGLIST (append OGLIST (cdr TMPLIST)))
            )
           )
           (setq C (+ C 1))
           (setq P1 P2)
          )
          (setq P2 (nth 2 NODE))
          (if (/= nil (setq TMPLIST (RFL:GETSURFACELINE P1 P2 OBSURFACE)))
           (if (= nil OGLIST)
            (setq OGLIST (append OGLIST TMPLIST))
            (setq OGLIST (append OGLIST (cdr TMPLIST)))
           )
          )
         )
        )
       )
      )
     )
     (if (/= nil OGLIST)
      (progn
       (command "._3DPOLY")
       (foreach NODE OGLIST
        (command NODE)
       )
       (command "")
      )
     )
    )
   )
  )
 )

 (setvar "CMDECHO" CMDECHO)
 (setvar "ANGBASE" ANGBASE)
 (setvar "ANGDIR" ANGDIR)
 (setvar "OSMODE" OSMODE)
 (setvar "ORTHOMODE" ORTHOMODE)
 (setq RFL:ALIGNLIST ALSAVE)

 ;; ---------------- drape summary ----------------
 (if (/= nil OGLIST)
  (progn
   (setq NVERT 0 EMIN nil EMAX nil)
   (foreach NODE OGLIST
    (setq NVERT (1+ NVERT))
    (setq Z (caddr NODE))
    (if (/= nil Z)
     (progn
      (if (or (= nil EMIN) (< Z EMIN))
       (setq EMIN Z)
      )
      (if (or (= nil EMAX) (> Z EMAX))
       (setq EMAX Z)
      )
     )
    )
   )
   (princ (strcat "\n\nDRAPEALIGN : " (itoa NVERT) " vertices added"))
   (if (/= nil EMIN)
    (princ (strcat "\n             elevation : min " (rtos EMIN 2 3)
                   "   max " (rtos EMAX 2 3)
				   "\n"))
   )
  )
 )
 (eval nil)
)
