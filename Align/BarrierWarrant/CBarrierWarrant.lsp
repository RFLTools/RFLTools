;
;
;     Program written by Robert Livingston, 2015-08-28
;
;     C:BARRIERWARRANT is a utility for analysing cross section and outputting a .csv to be used in the Barrier Warrant spreadsheet
;
;
(defun C:BARRIERWARRANT (/ *error* ANGBASE ANGDIR ATTREQ CMDECHO DAYLIGHTLIST GETDAYLIGHT NODE
                           OBSURFACE ORTHOMODE OSMODE OUTFILE REP ROADW S SECTIONLIST SECTIONSET
                           SLOPECUT SLOPEFILL STA STAEND STASTART STEP SUPERL SUPERR SWATH TMP Z)
 (setq ATTREQ (getvar "ATTREQ"))
 (setvar "ATTREQ" 0)
 (setq ANGBASE (getvar "ANGBASE"))
 (setvar "ANGBASE" 0.0)
 (setq ANGDIR (getvar "ANGDIR"))
 (setvar "ANGDIR" 1)
 (setq CMDECHO (getvar "CMDECHO"))
 (setvar "CMDECHO" 0)
 (setq OSMODE (getvar "OSMODE"))
 (setvar "OSMODE" 0)
 (setq ORTHOMODE (getvar "ORTHOMODE"))
 (setvar "ORTHOMODE" 0)

 (defun *error* (msg)
  (setvar "ATTREQ" ATTREQ)
  (setvar "ANGBASE" ANGBASE)
  (setvar "ANGDIR" ANGDIR)
  (setvar "CMDECHO" CMDECHO)
  (setvar "OSMODE" OSMODE)
  (setvar "ORTHOMODE" ORTHOMODE)
  (close OUTFILE)
  (print msg)
 )

 (defun GETDAYLIGHT (SECTIONLIST Z ROADWL SLOPECUTL SLOPEFILLL SUPERL ROADWR SLOPECUTR SLOPEFILLR SUPERR / C P1L P2LC P2LF P2RC P2RF PL PR TMP)
  (setq PL nil)
  (setq P1L (list (* -1.0 ROADWL) (+ Z (* ROADWL SUPERL 0.01))))
  (setq TMP (caar SECTIONLIST))
  (setq P2LC (list TMP (+ Z (/ (- (car P1L) TMP) SLOPECUTL))))
  (setq P2LF (list TMP (+ Z (/ (- TMP (car P1L)) SLOPEFILLL))))
  (setq PR nil)
  (setq P1R (list ROADWR (+ Z (* ROADWR SUPERR 0.01))))
  (setq TMP (car (last SECTIONLIST)))
  (setq P2RC (list TMP (+ Z (/ (- TMP (car P1R)) SLOPECUTR))))
  (setq P2RF (list TMP (+ Z (/ (- (car P1R) TMP) SLOPEFILLR))))
  (setq C 1)
  (while (and (< C (length SECTIONLIST)) (< (car (nth (- C 1) SECTIONLIST)) 0.0))
   (if (setq TMP (inters P1L P2LC (nth (- C 1) SECTIONLIST) (nth C SECTIONLIST)))
    (if (<= (car TMP) (* ROADWL -1.0))
     (setq PL TMP)
    )
   )
   (if (setq TMP (inters P1L P2LF (nth (- C 1) SECTIONLIST) (nth C SECTIONLIST)))
    (if (<= (car TMP) (* ROADWL -1.0))
     (setq PL TMP)
    )
   )
   (setq C (+ C 1))
  )
  (setq C (- (length SECTIONLIST) 1))
  (while (and (> C 0) (> (car (nth C SECTIONLIST)) 0.0))
   (if (setq TMP (inters P1R P2RC (nth (- C 1) SECTIONLIST) (nth C SECTIONLIST)))
    (if (>= (car TMP) ROADWL)
     (setq PR TMP)
    )
   )
   (if (setq TMP (inters P1R P2RF (nth (- C 1) SECTIONLIST) (nth C SECTIONLIST)))
    (if (>= (car TMP) ROADWL)
     (setq PR TMP)
    )
   )
   (setq C (- C 1))
  )
  (list P1L PL P1R PR)
 )

 (if RFL:ALIGNLIST
  (if RFL:PVILIST
   (if (setq OBSURFACE (RFL:GETC3DSURFACE))
    (progn
     (setq SWATH 250.0)
     (if (setq REP (getdist (strcat "\nEnter swath width : <" (rtos SWATH) "> : ")))
      (setq SWATH REP)
     )
     (setq ROADW 10.0)
     (setq SLOPECUT 2.0)
     (setq SLOPEFILL 2.0)
     (if (setq REP (getdist (strcat "\nEnter road width <" (rtos ROADW) "> : ")))
      (setq ROADW REP)
     )
     (if (setq REP (getdist (strcat "\nEnter cut slope X:1 <" (rtos SLOPECUT) "> : ")))
      (setq SLOPECUT REP)
     )
     (if (setq REP (getdist (strcat "\nEnter fill slope X:1 <" (rtos SLOPEFILL) "> : ")))
      (setq SLOPEFILL REP)
     )
     (setq STEP 20.0)
     (if (setq REP (getdist (strcat "\nEnter station step size : <" (rtos STEP) "> : ")))
      (setq STEP REP)
     )
     (setq STASTART (max (caar RFL:ALIGNLIST) (caar RFL:PVILIST)))
     (if (= nil (setq REP (getdist (strcat "\nEnter start station (min = " (rtos STASTART) ") <" (rtos (float (* STEP (+ 1 (fix (/ STASTART STEP)))))) "> : "))))
      (setq STASTART (float (* STEP (+ 1 (fix (/ STASTART STEP))))))
     )
     (setq STAEND (min (+ (caar RFL:ALIGNLIST) (RFL:GETALIGNLENGTH)) (car (last RFL:PVILIST))))
     (if (= nil (setq REP (getdist (strcat "\nEnter start end (max = " (rtos STAEND) ") <" (rtos (float (* STEP (fix (/ STAEND STEP))))) "> : "))))
      (setq STAEND (float (* STEP (fix (/ STAEND STEP)))))
     )
     (setq SECTIONSET (RFL:GETSECTIONSET STASTART STAEND SWATH STEP OBSURFACE RFL:ALIGNLIST))
     (setq STA STASTART)
     (princ (strcat "\nFile written to: " (getenv "UserProfile") "\\Documents\\" "BarrierWarrant.CSV"))
     (setq OUTFILE (open (strcat (getenv "UserProfile") "\\Documents\\" "BarrierWarrant.CSV") "w"))
     (while (<= STA STAEND)
      (princ (strcat "\nSta : " (RFL:STATXT STA)))
      (setq SECTIONLIST (cadr (assoc STA SECTIONSET)))
      (if SECTIONLIST
       (progn
        (setq Z (RFL:ELEVATION STA))
        (if RFL:SUPERLIST
         (if (setq S (RFL:SUPER STA))
          (setq SUPERL (car S) SUPERR (cadr S))
          (setq SUPERL 0.0 SUPERR 0.0)
         )
         (setq SUPERL 0.0 SUPERR 0.0)
        )
        (setq TMP (GETDAYLIGHT SECTIONLIST Z (/ ROADW 2.0) SLOPECUT SLOPEFILL SUPERL (/ ROADW 2.0) SLOPECUT SLOPEFILL SUPERR))
        (princ (strcat "\nSta : " (RFL:STATXT STA) ", R : " (rtos (RFL:GETRADIUS STA) 2 3) ", Grade : " (rtos (* (RFL:SLOPE STA) 100.0) 2 3) ", L Fill : " (rtos (- (cadr (car TMP)) (cadr (cadr TMP))) 2 3) ", R Fill = " (rtos (- (cadr (caddr TMP)) (cadr (cadddr TMP))) 2 3)))
        (princ (strcat (rtos STA 2 8) "," (rtos (RFL:GETRADIUS STA) 2 8) "," (rtos (* (RFL:SLOPE STA) 100.0) 2 8) "," (rtos (- (cadr (car TMP)) (cadr (cadr TMP))) 2 8) "," (rtos (- (cadr (caddr TMP)) (cadr (cadddr TMP))) 2 8) "\n") OUTFILE)
       )
      )
      (setq STA (+ STA STEP))
     )
     (close OUTFILE)
    )
    (princ "\n!!! No Surface Selected !!!")
   )
   (princ "\n!!! No Profile Defined !!!")
  )
  (princ "\n!!! No Alignment Defined !!!")
 )
 (setvar "ATTREQ" ATTREQ)
 (setvar "ANGBASE" ANGBASE)
 (setvar "ANGDIR" ANGDIR)
 (setvar "CMDECHO" CMDECHO)
 (setvar "OSMODE" OSMODE)
 (setvar "ORTHOMODE" ORTHOMODE)
)
