;
;
;   Program written by Robert Livingston, 98/05/14
;
;   PROF is a set of general profile utilities
;
;
(defun TAN (ANG)
 (eval (/ (sin ANG) (cos ANG)))
)
(defun RFLPROFDEF (/ PROFBLOCK TMP)
 (setq PROFDEF nil)
 (setq PROFBLOCK (ssget "X" (list (cons 0 "INSERT") (cons 2 "RFLPROF"))))
 (if (= nil PROFBLOCK)
  (princ "\n*** NO PROFILE BLOCK EXISTS IN DRAWING ***\n")
  (progn
   (if (> (sslength PROFBLOCK) 1)
    (progn
     (princ "\n*** MORE THAN ONE PROFILE BLOCK EXISTS IN DRAWING ***")
     (princ "\nSelect block for this definition")
     (setq PROFBLOCK (car (entsel)))
    )
    (setq PROFBLOCK (ssname PROFBLOCK 0))
   )
   (if (or (/= "INSERT" (cdr (assoc 0 (entget PROFBLOCK))))
           (/= "RFLPROF" (strcase (cdr (assoc 2 (entget PROFBLOCK))))))
    (print "\n*** ENTITY IS NOT A PROFILE DEFINITION BLOCK ***\n")
    (progn
     (setq PROFDEF (list (append (list "BPOINT") (cdr (assoc 10 (entget PROFBLOCK))))))
     (setq PROFBLOCK (entnext PROFBLOCK))
     (setq TMP (substr (cdr (assoc 1 (entget PROFBLOCK))) 1 1))
     (setq PROFDEF (append PROFDEF (list (cons (cdr (assoc 2 (entget PROFBLOCK)))
                                               (atof (cdr (assoc 1 (entget PROFBLOCK))))))))
     (setq PROFBLOCK (entnext PROFBLOCK))
     (setq PROFDEF (append PROFDEF (list (cons (cdr (assoc 2 (entget PROFBLOCK)))
                                               (* (if (= TMP "-") -1.0 1.0) (atof (cdr (assoc 1 (entget PROFBLOCK)))))))))
     (setq PROFBLOCK (entnext PROFBLOCK))
     (setq PROFDEF (append PROFDEF (list (cons (cdr (assoc 2 (entget PROFBLOCK)))
                                               (atof (cdr (assoc 1 (entget PROFBLOCK))))))))
     (setq PROFBLOCK (entnext PROFBLOCK))
     (setq PROFDEF (append PROFDEF (list (cons (cdr (assoc 2 (entget PROFBLOCK)))
                                               (atof (cdr (assoc 1 (entget PROFBLOCK))))))))
     (setq PROFBLOCK (entnext PROFBLOCK))
     (setq PROFDEF (append PROFDEF (list (cons (cdr (assoc 2 (entget PROFBLOCK)))
                                               (cdr (assoc 1 (entget PROFBLOCK)))))))
     (setq PROFBLOCK (entnext PROFBLOCK))
     (setq PROFDEF (append PROFDEF (list (cons (cdr (assoc 2 (entget PROFBLOCK)))
                                               (cdr (assoc 1 (entget PROFBLOCK)))))))
     (setq PROFBLOCK (entnext PROFBLOCK))
     (setq PROFDEF (append PROFDEF (list (cons (cdr (assoc 2 (entget PROFBLOCK)))
                                               (cdr (assoc 1 (entget PROFBLOCK)))))))
     (setq PROFBLOCK (entnext PROFBLOCK))
     (if (= (cdr (assoc 0 (entget PROFBLOCK))) "ATTRIB")
      (setq PROFDEF (append PROFDEF (list (cons (cdr (assoc 2 (entget PROFBLOCK)))
                                                (atof (cdr (assoc 1 (entget PROFBLOCK))))))))
     )
     (setq PROFBLOCK (entnext PROFBLOCK))
     (if (= (cdr (assoc 0 (entget PROFBLOCK))) "ATTRIB")
      (setq PROFDEF (append PROFDEF (list (cons (cdr (assoc 2 (entget PROFBLOCK)))
                                                (atoi (cdr (assoc 1 (entget PROFBLOCK))))))))
     )
    )
   )
  )
 )
)
;
;
; Old ELEVATION - superseded below
;
;(defun ELEVATION (STA / ANG C CMDECHO ELEV G G1 G2 L1 L2 L3 L4 P SIGN TMP)
; (setq CMDECHO (getvar "CMDECHO"))
; (setvar "CMDECHO" 0)
;
; (if (/= nil PVILIST)
;  (progn
;   (if (or (< STA (car (car PVILIST))) (> STA (car (nth (- (length PVILIST) 1) PVILIST))))
;    (progn
;     (princ "\n*** STATION OUT OF RANGE ***\n")
;     (setq ELEV nil)
;    )
;    (progn
;     (setq C 1)
;     (setq G1 (/ (- (cadr (nth C PVILIST))
;                    (cadr (nth (- C 1) PVILIST))
;                 )
;                 (- (car (nth C PVILIST))
;                    (car (nth (- C 1) PVILIST))
;                 )
;              )
;     )
;     (if (= (+ C 1) (length PVILIST))
;      (setq G2 0)
;      (setq G2 (/ (- (cadr (nth (+ C 1) PVILIST))
;                     (cadr (nth C PVILIST))
;                  )
;                  (- (car (nth (+ C 1) PVILIST))
;                     (car (nth C PVILIST))
;                  )
;               )
;      )
;     )
;     (setq G (- G2 G1))
;     (setq ANG (- (atan G2) (atan G1)))
;     (if (> G 0) (setq SIGN 1.0) (setq SIGN -1.0))
;     (if (= (caddr (nth C PVILIST)) "L")
;      (progn
;       (setq L3 (/ (cadddr (nth C PVILIST)) 2.0))
;       (setq L4 (/ (cadddr (nth C PVILIST)) 2.0))
;      )
;      (progn
;       (setq TMP (* (cadddr (nth C PVILIST))
;                  (TAN (/ (abs ANG) 2.0))
;               )
;       )
;       (setq L3 (* TMP (cos (atan (abs G1)))))
;       (setq L4 (* TMP (cos (atan (abs G2)))))
;      )
;     )
;     (while (> STA (+ (car (nth C PVILIST)) L4))
;      (setq C (+ C 1))
;      (setq G1 G2)
;      (if (= (+ C 1) (length PVILIST))
;       (setq G2 0)
;       (setq G2 (/ (- (cadr (nth (+ C 1) PVILIST))
;                      (cadr (nth C PVILIST))
;                   )
;                   (- (car (nth (+ C 1) PVILIST))
;                      (car (nth C PVILIST))
;                   )
;                )
;       )
;      )
;      (setq G (- G2 G1))
;      (setq ANG (- (atan G2) (atan G1)))
;      (if (> G 0) (setq SIGN 1.0) (setq SIGN -1.0))
;      (if (= (caddr (nth C PVILIST)) "L")
;       (progn
;        (setq L1 L3)
;        (setq L2 L4)
;        (setq L3 (/ (cadddr (nth C PVILIST)) 2.0))
;        (setq L4 (/ (cadddr (nth C PVILIST)) 2.0))
;       )
;       (progn
;        (setq L1 L3)
;        (setq L2 L4)
;        (setq TMP (* (cadddr (nth C PVILIST))
;                   (TAN (/ (abs ANG) 2.0))
;                )
;        )
;        (setq L3 (* TMP (cos (atan (abs G1)))))
;        (setq L4 (* TMP (cos (atan (abs G2)))))
;       )
;      )
;     )
;     (setq ELEV (+ (cadr (nth (- C 1) PVILIST))
;                   (* (- STA (car (nth (- C 1) PVILIST))) G1)))
;     (setq D (- STA (- (car (nth C PVILIST)) L3)))
;     (if (> D 0.0)
;      (progn
;       (if (= (caddr (nth C PVILIST)) "L")
;        (progn
;         (setq ELEV (+ ELEV (/ (* D D G) (* L3 4.0))))
;        )
;        (progn
;         (setq X (- (car (nth C PVILIST)) L3)
;         )
;         (setq Y (+ (cadr (nth C PVILIST))
;                    (* (- X (car (nth C PVILIST))) G1)
;                 )
;         )
;         (setq P (list (- X (* SIGN (cadddr (nth C PVILIST)) (sin (atan G1))))
;                       (+ Y (* SIGN (cadddr (nth C PVILIST)) (cos (atan G1))))
;                 )
;         )
;         (if (= SIGN 1.0)
;          (setq ELEV (- (cadr P)
;                        (sqrt (- (* (cadddr (nth C PVILIST))
;                                    (cadddr (nth C PVILIST))
;                                 )
;                                 (* (- STA (car P))
;                                    (- STA (car P))
;                                 )
;                              )
;                        )
;                     )
;          )
;          (setq ELEV (+ (cadr P)
;                        (sqrt (- (* (cadddr (nth C PVILIST))
;                                    (cadddr (nth C PVILIST))
;                                 )
;                                 (* (- STA (car P))
;                                    (- STA (car P))
;                                 )
;                              )
;                        )
;                     )
;          )
;         )
;        )
;       )
;      )
;     )
;    )
;   )
;  )
;  (progn
;   (princ "\n*** PROFILE NOT SET - RUN GPROF OR RPROF ***\n")
;   (setq ELEV nil)
;  )
; )
;
; (setvar "CMDECHO" CMDECHO)
; (eval ELEV)
;)
;(defun ELEVATION (STA / C CMDECHO ELEV ELEV1 ELEV2 ELEV3 G1 G2 L NODE P STA1 STA2 STA3)
; (setq CMDECHO (getvar "CMDECHO"))
; (setvar "CMDECHO" 0)
;
; (if (/= nil PVILIST)
;  (progn
;   (if (or (< STA (caar PVILIST)) (> STA (car (last PVILIST))))
;    (progn
;     (princ "\n*** STATION OUT OF RANGE ***\n")
;     (setq ELEV nil)
;    )
;    (progn
;     (setq C 1)
;     (while (> STA (+ (car (setq NODE (nth C PVILIST)))
;                      (/ (if (= nil (cadddr NODE)) 0.0 (cadddr NODE)) 2.0)
;                   )
;            )
;      (setq C (1+ C))
;     )
;     (if (or (= "L" (caddr (nth C PVILIST))) (= nil (caddr (nth C PVILIST))))
;      (progn
;       (setq NODE (nth (1- C) PVILIST))
;       (setq STA1 (car NODE))
;       (setq ELEV1 (cadr NODE))
;       (setq NODE (nth C PVILIST))
;       (setq STA2 (car NODE))
;       (setq ELEV2 (cadr NODE))
;       (setq L (if (= nil (cadddr NODE)) 0.0 (cadddr NODE)))
;       (setq G1 (/ (- ELEV2 ELEV1) (- STA2 STA1)))
;       (setq ELEV (+ ELEV1 (* G1 (- STA STA1))))
;       (setq D (- STA (- STA2 (/ L 2.0))))
;       (if (> D 0.0)
;        (progn
;         (setq NODE (nth (1+ C) PVILIST))
;         (setq STA3 (car NODE))
;         (setq ELEV3 (cadr NODE))
;         (setq G2 (/ (- ELEV3 ELEV2) (- STA3 STA2)))
;         (setq ELEV (+ ELEV (/ (* D D (- G2 G1)) (* L 2.0))))
;        )
;       )        
;      )
;      (progn
;       (princ "\n*** ONLY PARABILIC VERTICAL CURVES SUPPORTED ***\n")
;       (setq ELEV nil)
;      )
;     )
;    )
;   )
;  )
;  (progn
;   (princ "\n*** PROFILE NOT SET - RUN GPROF OR RPROF ***\n")
;   (setq ELEV nil)
;  )
; )
;
; (setvar "CMDECHO" CMDECHO)
; (eval ELEV)
;)
;
;
; Old SLOPE - superseded below
;
;(defun SLOPE (STA / ANG C CMDECHO G G1 G2 L1 L2 L3 L4 P SIGN SLOPEVAL TMP)
; (setq CMDECHO (getvar "CMDECHO"))
; (setvar "CMDECHO" 0)
;
; (if (/= nil PVILIST)
;  (progn
;   (if (or (< STA (car (car PVILIST))) (> STA (car (nth (- (length PVILIST) 1) PVILIST))))
;    (progn
;     (princ "\n*** STATION OUT OF RANGE ***\n")
;     (setq SLOPEVAL nil)
;    )
;    (progn
;     (setq C 1)
;     (setq G1 (/ (- (cadr (nth C PVILIST))
;                    (cadr (nth (- C 1) PVILIST))
;                 )
;                 (- (car (nth C PVILIST))
;                    (car (nth (- C 1) PVILIST))
;                 )
;              )
;     )
;     (if (= (+ C 1) (length PVILIST))
;      (setq G2 0)
;      (setq G2 (/ (- (cadr (nth (+ C 1) PVILIST))
;                     (cadr (nth C PVILIST))
;                  )
;                  (- (car (nth (+ C 1) PVILIST))
;                     (car (nth C PVILIST))
;                  )
;               )
;      )
;     )
;     (setq G (- G2 G1))
;     (setq ANG (- (atan G2) (atan G1)))
;     (if (> G 0) (setq SIGN 1.0) (setq SIGN -1.0))
;     (if (= (caddr (nth C PVILIST)) "L")
;      (progn
;       (setq L3 (/ (cadddr (nth C PVILIST)) 2.0))
;       (setq L4 (/ (cadddr (nth C PVILIST)) 2.0))
;      )
;      (progn
;       (setq TMP (* (cadddr (nth C PVILIST))
;                  (TAN (/ (abs ANG) 2.0))
;               )
;       )
;       (setq L3 (* TMP (cos (atan (abs G1)))))
;       (setq L4 (* TMP (cos (atan (abs G2)))))
;      )
;     )
;     (while (> STA (+ (car (nth C PVILIST)) L4))
;      (setq C (+ C 1))
;      (setq G1 G2)
;      (if (= (+ C 1) (length PVILIST))
;       (setq G2 0)
;       (setq G2 (/ (- (cadr (nth (+ C 1) PVILIST))
;                      (cadr (nth C PVILIST))
;                   )
;                   (- (car (nth (+ C 1) PVILIST))
;                      (car (nth C PVILIST))
;                   )
;                )
;       )
;      )
;      (setq G (- G2 G1))
;      (setq ANG (- (atan G2) (atan G1)))
;      (if (> G 0) (setq SIGN 1.0) (setq SIGN -1.0))
;      (if (= (caddr (nth C PVILIST)) "L")
;       (progn
;        (setq L1 L3)
;        (setq L2 L4)
;        (setq L3 (/ (cadddr (nth C PVILIST)) 2.0))
;        (setq L4 (/ (cadddr (nth C PVILIST)) 2.0))
;       )
;       (progn
;        (setq L1 L3)
;        (setq L2 L4)
;        (setq TMP (* (cadddr (nth C PVILIST))
;                   (TAN (/ (abs ANG) 2.0))
;                )
;        )
;        (setq L3 (* TMP (cos (atan (abs G1)))))
;        (setq L4 (* TMP (cos (atan (abs G2)))))
;       )
;      )
;     )
;     (setq SLOPEVAL G1)
;     (setq D (- STA (- (car (nth C PVILIST)) L3)))
;     (if (> D 0.0)
;      (progn
;       (if (= (caddr (nth C PVILIST)) "L")
;        (progn
;         (setq SLOPEVAL (+ SLOPEVAL (* (- G2 G1) (/ D (+ L3 L4)))))
;        )
;        (progn
;         (setq X (- (car (nth C PVILIST)) L3)
;         )
;         (setq Y (+ (cadr (nth C PVILIST))
;                    (* (- X (car (nth C PVILIST))) G1)
;                 )
;         )
;         (setq P (list (- X (* SIGN (cadddr (nth C PVILIST)) (sin (atan G1))))
;                       (+ Y (* SIGN (cadddr (nth C PVILIST)) (cos (atan G1))))
;                 )
;         )
;         (if (= SIGN 1.0)
;          (setq ELEV (- (cadr P)
;                        (sqrt (- (* (cadddr (nth C PVILIST))
;                                    (cadddr (nth C PVILIST))
;                                 )
;                                 (* (- STA (car P))
;                                    (- STA (car P))
;                                 )
;                              )
;                        )
;                     )
;          )
;          (setq ELEV (+ (cadr P)
;                        (sqrt (- (* (cadddr (nth C PVILIST))
;                                    (cadddr (nth C PVILIST))
;                                 )
;                                 (* (- STA (car P))
;                                    (- STA (car P))
;                                 )
;                              )
;                        )
;                     )
;          )
;         )
;        )
;       )
;      )
;     )
;    )
;   )
;  )
;  (progn
;   (princ "\n*** PROFILE NOT SET - RUN GPROF OR RPROF ***\n")
;   (setq SLOPEVAL nil)
;  )
; )
;
; (setvar "CMDECHO" CMDECHO)
; (eval SLOPEVAL)
;)
;(defun SLOPE (STA / C CMDECHO ELEV1 ELEV2 ELEV3 G G1 G2 L NODE P)
; (setq CMDECHO (getvar "CMDECHO"))
; (setvar "CMDECHO" 0)
;
; (if (/= nil PVILIST)
;  (progn
;   (if (or (< STA (caar PVILIST)) (> STA (car (last PVILIST))))
;    (progn
;     (princ "\n*** STATION OUT OF RANGE ***\n")
;     (if (< STA (caar PVILIST))
;      (setq G (/ (- (cadadr PVILIST) (cadar PVILIST)) (- (caadr PVILIST) (caar PVILIST))))
;      (setq G (/ (- (cadadr (reverse PVILIST)) (cadar (reverse PVILIST))) (- (caadr (reverse PVILIST)) (caar (reverse PVILIST)))))
;     )
;    )
;    (progn
;     (setq C 0)
;     (while (> STA (+ (car (setq NODE (nth C PVILIST)))
;                      (/ (cadddr NODE) 2.0)
;                   )
;            )
;      (setq C (1+ C))
;     )
;     (if (= "L" (caddr (nth C PVILIST)))
;      (progn
;       (setq NODE (nth (1- C) PVILIST))
;       (setq STA1 (car NODE))
;       (setq ELEV1 (cadr NODE))
;       (setq NODE (nth C PVILIST))
;       (setq STA2 (car NODE))
;       (setq ELEV2 (cadr NODE))
;       (setq L (cadddr NODE))
;       (setq G1 (/ (- ELEV2 ELEV1) (- STA2 STA1)))
;       (setq G G1)
;       (setq D (- STA (- STA2 (/ L 2.0))))
;       (if (> D 0.0)
;        (progn
;         (setq NODE (nth (1+ C) PVILIST))
;         (setq STA3 (car NODE))
;         (setq ELEV3 (cadr NODE))
;         (setq G2 (/ (- ELEV3 ELEV2) (- STA3 STA2)))
;         (setq G (+ G1 (* (/ D L) (- G2 G1))))
;        )
;       )        
;      )
;      (progn
;       (princ "\n*** ONLY PARABILIC VERTICAL CURVES SUPPORTED ***\n")
;       (setq ELEV nil)
;      )
;     )
;    )
;   )
;  )
;  (progn
;   (princ "\n*** PROFILE NOT SET - RUN GPROF OR RPROF ***\n")
;   (setq G nil)
;  )
; )
;
; (setvar "CMDECHO" CMDECHO)
; (eval G)
;)
(defun PROFPOINT (STA ELEV / D X Y)
 (if (/= nil PROFDEF)
  (progn
   (if (= (assoc "DIRECTION" PROFDEF) nil)
    (setq D 1)
    (setq D (cdr (assoc "DIRECTION" PROFDEF)))
   )
   (setq X (+ (* (- STA
                    (+ (* (cdr (assoc "STAH" PROFDEF)) 1000.0)
                       (cdr (assoc "STAL" PROFDEF))
                    )
                 )
                 D
              )
              (car (cdr (assoc "BPOINT" PROFDEF)))
           )
   )
   (setq Y (+ (* (- ELEV (cdr (assoc "ELEV" PROFDEF)))
                 (cdr (assoc "VEXAG" PROFDEF))
              )
              (cadr (cdr (assoc "BPOINT" PROFDEF)))
           )
   )
   (list X Y 0.0)
  )
  (progn
   (princ "\n*** PROFILE NOT SET - RUN GPROF OR RPROF ***\n")
   (eval nil)
  )
 )
)
(defun C:PROFLINE (/ STA ELEV)
 (setq CMDECHO (getvar "CMDECHO"))
 (setvar "CMDECHO" 0)

 (if (/= nil PROFDEF)
  (progn
   (command ".PLINE")
   (setq STA (getstring "\nStation:"))
   (while (/= STA "")
    (if (= (strcase STA) "U")
     (progn
      (command "U")
     )
     (progn
      (setq STA (atof STA))
      (setq ELEV (atof (getstring "\nElevation:")))
      (command (PROFPOINT STA ELEV))
     )
    )
    (setq STA (getstring "\nStation:"))
   )
  )
  (progn
   (princ "\n*** PROFILE NOT SET - RUN GPROF OR RPROF ***\n")
  )
 )

 (setvar "CMDECHO" CMDECHO)
)
