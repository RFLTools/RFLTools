;
;
;   Program written by Robert Livingston, 99/11/15
;
;   RFL:DRAWPROF draws the current profile as defined in RFL:PVILIST
;
;
(defun RFL:DRAWPROF ( RFL:PVILIST / ACTIVEDOC ACTIVESPACE ANG BULGE C C2 CLAYER ENT ENTLIST G G1 G2 K
                                    L L1 L2 L3 L4 P1 P2 P3 PLINETYPE PREVENT SIGN STA STA1 STA2 TMP)
 (setq CLAYER (getvar "CLAYER"))
 
 (setq PREVENT nil)

 (vl-load-com)
 (setq ACTIVEDOC (vla-get-activedocument (vlax-get-acad-object)))
 (setq ACTIVESPC
       (vlax-get-property ACTIVEDOC
        (if (or (eq acmodelspace (vla-get-activespace ACTIVEDOC)) (eq :vlax-true (vla-get-mspace ACTIVEDOC)))
         'modelspace
         'paperspace
        )
       )
 )

 (if (= nil RFL:PROFDEFLIST)
  (princ "\n*** Profile not set ***")
  (progn
   (if (= (tblsearch "BLOCK" "PVI2") nil)
    (progn
     (princ "\n*** Creating LDD PVI node ***")
     (RFL:MAKEENT "PVI2")
    )
   )
     (setq C 0)
     (if (not (tblsearch "LAYER" (cdr (assoc "PLAYER" RFL:PROFDEFLIST))))
      (entmake (list (cons 0 "LAYER")
                     (cons 100 "AcDbSymbolTableRecord")
                     (cons 100 "AcDbLayerTableRecord")
                     (cons 2 (cdr (assoc "PLAYER" RFL:PROFDEFLIST)))
                     (cons 70 0)
               )
      )
     )
     (setvar "CLAYER" (cdr (assoc "PLAYER" RFL:PROFDEFLIST)))
     (if (= nil (tblsearch "BLOCK" "PVI2")) (RFL:MAKEENT "PVI2"))
     (while (< C (length RFL:PVILIST))
      (vla-insertblock ACTIVESPC
                       (vlax-3D-point (RFL:PROFPOINT (nth 0 (nth C RFL:PVILIST)) (nth 1 (nth C RFL:PVILIST))))
                       "PVI2"
                       25.4
                       25.4
                       25.4
                       0.0
      )
      (setq ENT (entlast))
      (RFL:PUTPREVENT ENT PREVENT)(RFL:PUTNEXTENT PREVENT ENT)(setq PREVENT ENT)
      (setq ENTLIST (entget ENT))
      (if (= (cdr (assoc 66 ENTLIST)) 1)
       (progn
        (if (or (= C 0) (= C (- (length RFL:PVILIST) 1)))
         (progn
          (setq L 0.0 K 0.0)
         )
         (progn
          (setq L (nth 3 (nth C RFL:PVILIST)))
          (setq G1 (/ (- (nth 1 (nth C RFL:PVILIST))
                         (nth 1 (nth (- C 1) RFL:PVILIST))
                      )
                      (- (nth 0 (nth C RFL:PVILIST))
                         (nth 0 (nth (- C 1) RFL:PVILIST))
                      )
                   )
          )
          (setq G2 (/ (- (nth 1 (nth (+ C 1) RFL:PVILIST))
                         (nth 1 (nth C RFL:PVILIST))
                      )
                      (- (nth 0 (nth (+ C 1) RFL:PVILIST))
                         (nth 0 (nth C RFL:PVILIST))
                      )
                   )
          )
          (if (= G1 G2)
           (setq K 0.0)
           (setq K (abs (/ L (- G2 G1) 100.0)))
          )
         )
        )
        (while (/= (cdr (assoc 0 ENTLIST)) "SEQEND")
         (if (= (cdr (assoc 2 ENTLIST)) "LENGTH")
          (progn
           (setq ENTLIST (subst (cons 1 (rtos L 2 8)) (assoc 1 ENTLIST) ENTLIST))
           (entmod ENTLIST)
           (entupd ENT)
          )
         )
         (if (= (cdr (assoc 2 ENTLIST)) "K")
          (progn
           (setq ENTLIST (subst (cons 1 (rtos K 2 8)) (assoc 1 ENTLIST) ENTLIST))
           (entmod ENTLIST)
           (entupd ENT)
          )
         )
         (setq ENT (entnext ENT))
         (setq ENTLIST (entget ENT))
        )
       )
      )
      (setq C (+ C 1))
     )
   (setq C 1)
   (setq G1 (/ (- (nth 1 (nth C RFL:PVILIST))
                  (nth 1 (nth (- C 1) RFL:PVILIST))
               )
               (- (nth 0 (nth C RFL:PVILIST))
                  (nth 0 (nth (- C 1) RFL:PVILIST))
               )
            )
   )
   (if (= (+ C 1) (length RFL:PVILIST))
    (setq G2 0)
    (setq G2 (/ (- (nth 1 (nth (+ C 1) RFL:PVILIST))
                   (nth 1 (nth C RFL:PVILIST))
                )
                (- (nth 0 (nth (+ C 1) RFL:PVILIST))
                   (nth 0 (nth C RFL:PVILIST))
                )
             )
    )
   )
   (setq G (- G2 G1))
   (setq ANG (- (atan G2) (atan G1)))
   (if (> G 0) (setq SIGN 1.0) (setq SIGN -1.0))
   (if (= (nth 2 (nth C RFL:PVILIST)) "L")
    (progn
     (setq L3 (/ (nth 3 (nth C RFL:PVILIST)) 2.0))
     (setq L4 (/ (nth 3 (nth C RFL:PVILIST)) 2.0))
    )
    (progn
     (setq TMP (* (nth 3 (nth C RFL:PVILIST))
                (RFL:TAN (/ (abs ANG) 2.0))
             )
     )
     (setq L3 (* TMP (cos (atan (abs G1)))))
     (setq L4 (* TMP (cos (atan (abs G2)))))
    )
   )
   (setq STA1 (nth 0 (nth (- C 1) RFL:PVILIST)))
   (setq STA2 (- (nth 0 (nth C RFL:PVILIST)) L3))
   (command "._LINE"
            (RFL:PROFPOINT STA1 (RFL:ELEVATION STA1))
            (RFL:PROFPOINT STA2 (RFL:ELEVATION STA2))
            ""
   )
   (setq ENT (entlast))(RFL:PUTPREVENT ENT PREVENT)(RFL:PUTNEXTENT PREVENT ENT)(setq PREVENT ENT)
   (while (< C (- (length RFL:PVILIST) 1))
    (setq C (+ C 1))
    (setq G1 G2)
    (if (= (+ C 1) (length RFL:PVILIST))
     (setq G2 0)
     (setq G2 (/ (- (nth 1 (nth (+ C 1) RFL:PVILIST))
                    (nth 1 (nth C RFL:PVILIST))
                 )
                 (- (nth 0 (nth (+ C 1) RFL:PVILIST))
                    (nth 0 (nth C RFL:PVILIST))
                 )
              )
     )
    )
    (setq G (- G2 G1))
    (setq ANG (- (atan G2) (atan G1)))
    (if (> G 0) (setq SIGN 1.0) (setq SIGN -1.0))
    (if (= (nth 2 (nth C RFL:PVILIST)) "L")
     (progn
      (setq L1 L3)
      (setq L2 L4)
      (setq L3 (/ (nth 3 (nth C RFL:PVILIST)) 2.0))
      (setq L4 (/ (nth 3 (nth C RFL:PVILIST)) 2.0))
     )
     (progn
      (setq L1 L3)
      (setq L2 L4)
      (setq TMP (* (nth 3 (nth C RFL:PVILIST))
                 (RFL:TAN (/ (abs ANG) 2.0))
              )
      )
      (setq L3 (* TMP (cos (atan (abs G1)))))
      (setq L4 (* TMP (cos (atan (abs G2)))))
     )
    )
    (if (> (+ L1 L2) 0.0)
     (progn
      (entmake)
      (setq STA1 (- (nth 0 (nth (- C 1) RFL:PVILIST)) L1))
      (setq STA2 (+ (nth 0 (nth (- C 1) RFL:PVILIST)) L2))
      (RFL:DRAWPARABOLICVCURVE (RFL:PROFPOINT STA1 (RFL:ELEVATION STA1))
                               (RFL:PROFPOINT (nth 0 (nth (- C 1) RFL:PVILIST)) (nth 1 (nth (- C 1) RFL:PVILIST)))
                               (RFL:PROFPOINT STA2 (RFL:ELEVATION STA2))
      )
      (setq ENT (entlast))(RFL:PUTPREVENT ENT PREVENT)(RFL:PUTNEXTENT PREVENT ENT)(setq PREVENT ENT)
     )
    )
    (setq STA1 (+ (nth 0 (nth (- C 1) RFL:PVILIST)) L2))
    (setq STA2 (- (nth 0 (nth C RFL:PVILIST)) L3))
    (command "._LINE"
             (RFL:PROFPOINT STA1 (RFL:ELEVATION STA1))
             (RFL:PROFPOINT STA2 (RFL:ELEVATION STA2))
             ""
    )
    (setq ENT (entlast))(RFL:PUTPREVENT ENT PREVENT)(RFL:PUTNEXTENT PREVENT ENT)(setq PREVENT ENT)
   )
  )
 )
 (setvar "CLAYER" CLAYER)
)
