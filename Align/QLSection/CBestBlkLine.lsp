;
;
;     Program written by Robert Livingston, 2020-01-14
;
;     C:BESTBLKLINE is a routine for finding best lines withing QLSection point blocks
;
;
(defun C:BESTBLKLINE (/ BESTLINE BLKLIST GETBOXPOINT P P0 P1 P2 P3 P4 PLIST SWATH)
 (defun GETPLIST (P1 P2 SWATH BLKLIST / ANG D P P3 P4 PLIST)
  (setq PLIST nil)
  (setq D (distance P1 P2))
  (setq ANG (angle P1 P2))
  (setq P (list (/ (+ (car P1) (car P2)) 2.0) (/ (+ (cadr P1) (cadr P2)) 2.0)))
  (setq P3 (list (+ (car P) (* (/ SWATH 2.0) (cos (+ ANG (/ pi 2.0)))))
                 (+ (cadr P) (* (/ SWATH 2.0) (sin (+ ANG (/ pi 2.0)))))
           )
  )
  (setq P4 (list (+ (car P) (* (/ SWATH 2.0) (cos (- ANG (/ pi 2.0)))))
                 (+ (cadr P) (* (/ SWATH 2.0) (sin (- ANG (/ pi 2.0)))))
           )
  )
  (foreach P BLKLIST
   (if (and (<= (abs (/ (+ (- (* (- (cadr P2) (cadr P1)) (car P))
                              (* (- (car P2) (car P1)) (cadr P))
                           )
                           (- (* (car P2) (cadr P1)) (* (cadr P2) (car P1)))
                        )
                        D
                     )
                )
                (/ SWATH 2.0)
            )
            (<= (abs (/ (+ (- (* (- (cadr P4) (cadr P3)) (car P))
                              (* (- (car P4) (car P3)) (cadr P))
                           )
                           (- (* (car P4) (cadr P3)) (* (cadr P4) (car P3)))
                        )
                        SWATH
                     )
                )
                (/ D 2.0)
            )
       )
       (setq PLIST (append PLIST (list P)))
   )
  )
  (vl-sort PLIST (function (lambda (e1 e2) (< (distance e1 P1) (distance e2 P1)))))
 )
 (defun GETBOXPOINT (P0 SWATH / ANG D FLAG GRR P P1 P2 P3 P4)
  (princ "\nPoint : ")
  (setq P nil)
  (setq FLAG T)
  (while (and FLAG (/= 3 (car (setq GRR (grread 5)))))
   (if P
    (progn
     (grdraw P1 P2 -1)
     (grdraw P2 P4 -1)
     (grdraw P4 P3 -1)
     (grdraw P3 P1 -1)
    )
   )
   (if (= 2 (car GRR))
    (setq P nil FLAG nil)
    (progn
     (setq P (cadr GRR))
     (setq D (distance P0 P))
     (setq ANG (angle P0 P))
     (setq P1 (list (+ (car P0) (* (/ SWATH 2.0) (cos (- ANG (/ pi 2.0)))))
                    (+ (cadr P0) (* (/ SWATH 2.0) (sin (- ANG (/ pi 2.0)))))
              )
     )
     (setq P2 (list (+ (car P) (* (/ SWATH 2.0) (cos (- ANG (/ pi 2.0)))))
                    (+ (cadr P) (* (/ SWATH 2.0) (sin (- ANG (/ pi 2.0)))))
              )
     )
     (setq P3 (list (+ (car P0) (* (/ SWATH 2.0) (cos (+ ANG (/ pi 2.0)))))
                    (+ (cadr P0) (* (/ SWATH 2.0) (sin (+ ANG (/ pi 2.0)))))
              )
     )
     (setq P4 (list (+ (car P) (* (/ SWATH 2.0) (cos (+ ANG (/ pi 2.0)))))
                    (+ (cadr P) (* (/ SWATH 2.0) (sin (+ ANG (/ pi 2.0)))))
              )
     )
     (grdraw P1 P2 -1)
     (grdraw P2 P4 -1)
     (grdraw P4 P3 -1)
     (grdraw P3 P1 -1)
    )
   )
  )
  (grdraw P1 P2 -1)
  (grdraw P2 P4 -1)
  (grdraw P4 P3 -1)
  (grdraw P3 P1 -1)
  P
 )
 (if (setq BLKLIST (RFL:GETBLKPLIST (car (entsel "\nSelect point block (<return> to use last point set) : "))))
  (progn
   (princ (strcat "\n" (itoa (length BLKLIST))))
   (setq SWATH (getdist "\nEnter swath width <0.25> : "))
   (if (= nil SWATH) (setq SWATH 0.5))
   (while (setq P0 (getpoint "\nStart point : "))
    (while (setq P (GETBOXPOINT P0 SWATH))
     (if (setq PLIST (GETPLIST P0 P SWATH BLKLIST))
      (progn
       (setq BESTLINE (RFL:BESTLINE PLIST))
       (entmake (list (cons 0 "LINE")
                      (cons 10 (car BESTLINE))
                      (cons 11 (cadr BESTLINE))
                )
       )
      )
     )
     (setq P0 P)
    )
   )
  )
 )
 T
)
