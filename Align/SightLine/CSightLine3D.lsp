;
;
;     Program written by Robert Livingston, 12-01-31
;
;     C:SIGHTLINE3D is a routine for drawing lines point to point along an alignment at a given length and checking for elevation conflicts
;
;
(defun C:SIGHTLINE3D (/ *error* 3DPENT 3DPENTLIST 3DPFLAG ALSAVE BARRIERFLAG BELOWFLAG BELOWLIST DIST DISTMIN PVISAVE ESAVE ANGBASE ANGDIR BARRIERAL BARRIERALLIST
                        CECOLOR CMDECHO CONTROLAL DRAWLINES ENT ENT2 ENTLIST GETBARRIERALLIST GETFROMLIST GETPTZ HEYE HTARGET HBARRIER L LAYERFLAG
                        OBSURFACE OSMODE P P1 P2 SIGHTAL STA STEP STEPFINE TMP TMPENT TOL)
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setvar "OSMODE" 0)
 (setq CECOLOR (getvar "CECOLOR"))
 (setq CLAYER (getvar "CLAYER"))
 (setq TOL 0.000001)

 (setq ALSAVE RFL:ALIGNLIST PVISAVE RFL:PVILIST ESAVE RFL:SUPERLIST)

 (defun *error* (msg)
  (princ msg)
  (setvar "CMDECHO" CMDECHO)
  (setvar "ANGBASE" ANGBASE)
  (setvar "ANGDIR" ANGDIR)
  (setvar "OSMODE" OSMODE)
  (setvar "CECOLOR" CECOLOR)
  (setvar "CLAYER" CLAYER)
  (setq RFL:ALIGNLIST ALSAVE RFL:PVILIST PVISAVE RFL:SUPERLIST ESAVE)
  ;(setq *error* nil)
 )

 (if (= nil VLAX-CREATE-OBJECT) (vl-load-com))

 (defun GETBARRIERALLIST ()
  (while (/= (setq ENT2 (car (entsel "\nSelect barrier polyline (<Return> when done) : "))) nil)
   (if (= nil ENT)
    (setq HBARRIER 0.0)
    (progn
     (setq HBARRIER (getreal "\nEnter target height (median = 0.810 / shoulder = 0.690) <0.690> : "))
     (if (= nil HBARRIER) (setq HBARRIER 0.690))
    )
   )
   (setq ENTLIST (entget ENT2))
   (if (= "POLYLINE" (cdr (assoc 0 ENTLIST)))
    (progn
     (command "._CONVERT" "P" "S" ENT2 "")
     (setq ENTLIST (entget ENT2))
    )
   )
   (if (/= "LWPOLYLINE" (cdr (assoc 0 ENTLIST)))
    (progn
     (princ "*** ERROR : NOT A POLYLINE ***")
    )
    (progn
     (setq BARRIERALLIST (append BARRIERALLIST (list (list HBARRIER (RFL:ALIGNDEF ENT2 (cdr (assoc 10 ENTLIST)) 0.0)))))
    )
   )
  )
 )

 (defun GETPTZ (P / OFFSETC STAC SUPERC TMP Z ZC)
  (setq RFL:ALIGNLIST CONTROLAL)
  (setq Z nil)
  (setq TMP (RFL:STAOFF P))
  (if (/= nil TMP)
   (progn
    (setq STAC (car TMP))
    (setq OFFSETC (cadr TMP))
    (setq ZC (RFL:ELEVATION STAC))
    (if (/= nil ZC)
      (progn
      (setq SUPERC (RFL:SUPER STAC))
      (if (/= nil SUPERC)
       (progn
        (if (< OFFSETC 0.0)
         (setq SUPERC (car SUPERC))
         (setq SUPERC (cadr SUPERC))
        )
        (setq Z (+ ZC (* (abs OFFSETC) SUPERC 0.01)))
       )
      )
     )
    )
   )
  )
  (setq RFL:ALIGNLIST SIGHTAL)
  (setq Z Z)
 )

 (defun DRAWLINES (CHECKBARRIER CHECKELEV OBSURFACE / ENT FILEFIRST INFILE INLINE NODE NODEAL OUTFILE P P1 P2 PCHECK PM PREVENT STA STA1 STA2 STAM STAEND Z1 Z2 ZC ZC1 ZC2)
  (setq PREVENT nil)
  (setq RFL:ALIGNLIST SIGHTAL)
  (setq STA (caar RFL:ALIGNLIST))
  (setq STAEND (+ STA (RFL:GETALIGNLENGTH)))
  (setq FILEFIRST T)
  (while (and (< STA STAEND)
              (>= DIST DISTMIN))
   (if LAYERFLAG
    (progn
     (if (= nil (tblsearch "LAYER" (strcat CLAYER "_" (itoa (fix DIST)))))
      (progn
;       (command "._LAYER" "M" (strcat CLAYER "_" (itoa (fix DIST))) "Off" (strcat CLAYER "_" (itoa (fix DIST))) "Yes" "")
       (entmake (list (cons 0 "LAYER")
                      (cons 100 "AcDbSymbolTableRecord")
                      (cons 100 "AcDbLayerTableRecord")
                      (cons 2 (strcat CLAYER "_" (itoa (fix DIST))))
                      (cons 62 -7)
                      (cons 70 0)
                )
       )
      )
     )
     (princ "\r                                      ")
     (princ (strcat "\rSolving for : " (itoa (fix DIST))))
     (setvar "CLAYER" (strcat CLAYER "_" (itoa (fix DIST))))
    )
   )
   (setq BELOWFLAG nil)
   (setq P (RFL:XY (list STA 0.0)))
   (if (/= nil P)
    (progn
     (setq STAM (RFL:SIGHTDIST STA DIST))
     (if (= STAM nil)
      (setq PM nil)
      (setq PM (RFL:XY (list STAM 0.0)))
     )
     (if (/= nil PM)
      (progn
       (setq Z1 0.0 Z2 0.0)
       (if CHECKELEV
        (progn
         (setq Z1 (GETPTZ P))
         (setq Z2 (GETPTZ PM))
         (if (or (= nil Z1) (= nil Z2))
          (setq Z1 0.0 Z2 0.0)
         (setq Z1 (+ Z1 HEYE) Z2 (+ Z2 HTARGET))
         )
        )
       )
       (setq BARRIERFLAG nil)
       (if CHECKBARRIER
        (foreach NODE2 BARRIERALLIST
         (progn
          (setq HBARRIER (car NODE2))
          (setq BARRIERAL (cadr NODE2))
          (foreach NODE BARRIERAL
           (progn
            (setq PCHECK (RFL:INTERS2 (list 0.0 P PM 0.0) NODE))
            (if (/= nil PCHECK)
             (progn
              (setq BARRIERFLAG T)
              (setq ZC1 0.0 ZC2 0.0)
              (setvar "CECOLOR" "RGB:255,255,0")
              (if (listp (car PCHECK))
               (progn
                (if (/= Z1 0.0)
                 (progn
                  (setq ZC (GETPTZ (car PCHECK)))
                  (setq ZC1 (+ ZC HBARRIER))
                  (setq ZC2 (+ Z1 (* (- Z2 Z1) (/ (distance P (car PCHECK)) (distance P PM)))))
                  (if (> ZC2 ZC1)
                   (setvar "CECOLOR" "RGB:0,255,0")
                   (setvar "CECOLOR" "RGB:255,0,0")
                  )
                 )
                )
;                (command "._POINT" (list (car (car PCHECK)) (cadr (car PCHECK)) ZC2))
                (entmake (list (cons 0 "POINT")
                               (append (list 10) (list (car (car PCHECK)) (cadr (car PCHECK)) ZC2))
                         )
                )
                (setq ENT (entlast))
                (RFL:PUTPREVENT ENT PREVENT)(RFL:PUTNEXTENT PREVENT ENT)(setq PREVENT ENT)
                (if (/= Z1 0.0)
                 (progn
                  (setq ZC (GETPTZ (cadr PCHECK)))
                  (setq ZC1 (+ ZC HBARRIER))
                  (setq ZC2 (+ Z1 (* (- Z2 Z1) (/ (distance P (cadr PCHECK)) (distance P PM)))))
                  (if (> ZC2 ZC1)
                   (setvar "CECOLOR" "RGB:0,255,0")
                   (setvar "CECOLOR" "RGB:255,0,0")
                  )
                 )
                )
;                (command "._POINT" (list (car (cadr PCHECK)) (cadr (cadr PCHECK)) ZC2))
                (entmake (list (cons 0 "POINT")
                               (append (list 10) (list (car (cadr PCHECK)) (cadr (cadr PCHECK)) ZC2))
                         )
                )
                (setq ENT (entlast))
                (RFL:PUTPREVENT ENT PREVENT)(RFL:PUTNEXTENT PREVENT ENT)(setq PREVENT ENT)
               )
               (progn
                (if (/= Z1 0.0)
                 (progn
                  (setq ZC (GETPTZ PCHECK))
                  (setq ZC1 (+ ZC HBARRIER))
                  (setq ZC2 (+ Z1 (* (- Z2 Z1) (/ (distance P PCHECK) (distance P PM)))))
                  (if (> ZC2 ZC1)
                   (setvar "CECOLOR" "RGB:0,255,0")
                   (setvar "CECOLOR" "RGB:255,0,0")
                  )
                 )
                )
                (if (/= "RGB:0,255,0" (getvar "CECOLOR")) (setq BELOWFLAG T))
;                (command "._POINT" (list (car PCHECK) (cadr PCHECK) ZC2))
                (entmake (list (cons 0 "POINT")
                               (append (list 10) (list (car PCHECK) (cadr PCHECK) ZC2))
                         )
                )
                (setq ENT (entlast))
                (RFL:PUTPREVENT ENT PREVENT)(RFL:PUTNEXTENT PREVENT ENT)(setq PREVENT ENT)
               )
              )
              (setvar "CECOLOR" CECOLOR)
             )
            )
           )
          )
         )
        )
       )
       (if BARRIERFLAG (setvar "CECOLOR" "RGB:255,255,0"))
;       (command "._LINE" (list (car P) (cadr P) Z1) (list (car PM) (cadr PM) Z2) "")
       (entmake (list (cons 0 "LINE")
                      (append (list 10) (list (car P) (cadr P) Z1))
                      (append (list 11) (list (car PM) (cadr PM) Z2))
                )
       )
       (setvar "CECOLOR" CECOLOR)
       (if (= nil OBSURFACE)
        (progn
         (setq ENT (entlast))
         (RFL:PUTPREVENT ENT PREVENT)(RFL:PUTNEXTENT PREVENT ENT)(setq PREVENT ENT)
        )
        (progn
         (setq ENT (entlast))
         (if (= T (RFL:SURFACELINE OBSURFACE ENT)) (setq BELOWFLAG T))
         (entdel ENT)
         (setq ENT (entlast))
         ;(RFL:PUTPREVENT (RFL:GETFIRSTENT ENT) PREVENT)(RFL:PUTNEXTENT PREVENT (RFL:GETFIRSTENT ENT))(setq PREVENT ENT)
        )
       )
      )
     )
    )
   )
   (setq BELOWLIST (append BELOWLIST (list (list STA BELOWFLAG))))
   (setq STA (+ STA STEP))
   (if (>= STA STAEND)
    (progn
     (if FILEFIRST
      (progn
       (princ (strcat "\nSight distances stored in : " (getenv "UserProfile") "\\Documents\\" "SIGHTLINE3D.CSV\n"))
       (setq OUTFILE (open (strcat (getenv "UserProfile") "\\Documents\\" "SIGHTLINE3D.CSV") "w"))
       (princ (strcat "Station,Offset," (rtos DIST 2 3)) OUTFILE)
       (foreach NODE BELOWLIST
        (progn
         (setq RFL:ALIGNLIST SIGHTAL)
         (setq P (RFL:XY (list (car NODE) 0.0)))
         (if (= CONTROLAL nil)
          (progn
           (setq P (list (car NODE) 0.0))
          )
          (progn
           (setq RFL:ALIGNLIST CONTROLAL)
           (setq P (RFL:STAOFF P))
           (setq RFL:ALIGNLIST SIGHTAL)
          )
         )
         (princ (strcat "\n" (rtos (car P) 2 3) "," (rtos (cadr P) 2 3)) OUTFILE)
         (if (cadr NODE)
          (princ ",ISSUE" OUTFILE)
          (princ ",OK" OUTFILE)
         )
        )
       )
       (close OUTFILE)
       (setq RFL:ALIGNLIST SIGHTAL)
       (setq FILEFIRST nil)
      )
      (progn
       (setq INFILE (open (strcat (getenv "UserProfile") "\\Documents\\" "SIGHTLINE3D.CSV") "r"))
       (setq INLINE (read-line INFILE))
       (setq OUTFILE (open (strcat (getenv "UserProfile") "\\Documents\\" "SIGHTLINE3Dtmp.CSV") "w"))
       (princ (strcat INLINE "," (rtos DIST 2 3)) OUTFILE)
       (foreach NODE BELOWLIST
        (if (/= nil (setq INLINE (read-line INFILE)))
         (progn
          (if (cadr NODE)
           (princ (strcat "\n" INLINE ",ISSUE") OUTFILE)
           (princ (strcat "\n" INLINE ",OK") OUTFILE)
          )
         )
        )
       )
       (close INFILE)
       (close OUTFILE)
       (vl-file-delete (strcat (getenv "UserProfile") "\\Documents\\" "SIGHTLINE3D.CSV"))
       (vl-file-rename (strcat (getenv "UserProfile") "\\Documents\\" "SIGHTLINE3Dtmp.CSV")
                       (strcat (getenv "UserProfile") "\\Documents\\" "SIGHTLINE3D.CSV")
       )
      )
     )
     (setq BELOWLIST nil)
     (setq STA (caar RFL:ALIGNLIST))
     (setq DIST (- DIST STEP))
    )
   )
  )
 )

 (command "._UNDO" "M")

 (setq BELOWLIST nil)
 (setq ENT (entsel "\nSelect lane center polyline (near start point) : "))
 (if (/= nil ENT)
  (progn
   (setq P (cadr ENT))
   (setq ENT (car ENT))
   (setq ENTLIST (entget ENT))
   (setq 3DPFLAG nil)
   (if (= "POLYLINE" (cdr (assoc 0 ENTLIST)))
    (if (/= 0 (logand (cdr (assoc 70 ENTLIST)) 8))
     (progn
      (initget "Yes No")
      (if (= "Yes" (getkword "\nA 3D POLYLINE has been selected would you like to use it for horizontal and vertical control (Y/N) : "))
       (setq 3DPFLAG ENT)
       (alert "Entity must be a 2D POLYLINE!")
      )
     )
     (progn
      (command "._CONVERT" "P" "S" ENT "")
      (setq ENTLIST (entget ENT))
     )
    )
   )
   (if (and (= nil 3DPFLAG) (/= "LWPOLYLINE" (cdr (assoc 0 ENTLIST))))
    (progn
     (princ "*** ERROR : NOT A 2D POLYLINE ***")
    )
    (progn
     (if (/= nil 3DPFLAG)
      (progn
       (setq 3DPENT (entnext ENT))
       (setq 3DPENTLIST (entget 3DPENT))
       (setq P1 (cdr (assoc 10 3DPENTLIST)))
       (setq P1 (list (car P1) (cadr P1)))
       (command "._PLINE")
       (while (= "VERTEX" (cdr (assoc 0 3DPENTLIST)))
        (setq P2 (cdr (assoc 10 3DPENTLIST)))
        (setq P2 (list (car P2) (cadr P2)))
        (command P2)
        (setq 3DPENT (entnext 3DPENT))
        (setq 3DPENTLIST (entget 3DPENT))
       )
       (command "")
       (setq ENT (entlast))
       (setq ENTLIST (entget ENT))
       (if (= "POLYLINE" (cdr (assoc 0 ENTLIST)))
        (progn
         (command "._CONVERT" "P" "S" ENT "")
         (setq ENTLIST (entget ENT))
        )
       )
      )
     )
     (setq P1 (cdr (assoc 10 ENTLIST)))
     (setq P2 (cdr (assoc 10 (reverse ENTLIST))))
     (if (< (distance P P1) (distance P P2))
      (setq SIGHTAL (RFL:ALIGNDEF ENT P1 0.0))
      (setq SIGHTAL (RFL:ALIGNDEF ENT P2 0.0))
     )
     (if (/= nil 3DPENT)
      (entdel ENT)
     )
     (setq DIST 0.0)
     (while (or (= DIST 0.0) (= DIST nil))
      (setq TMP (getdist "\nEnter sight length <250.0> : "))
      (if (= nil TMP)
       (setq DIST 250.0)
       (setq DIST TMP)
      )
     )
     (setq DISTMIN 0.0)
     (while (or (= DISTMIN 0.0) (= DISTMIN nil))
      (setq TMP (getdist (strcat "\nEnter minimum sight length for iterative analysis <" (rtos DIST 2 1) "> : ")))
      (if (= nil TMP)
       (setq DISTMIN DIST)
       (setq DISTMIN TMP)
      )
      (if (> DISTMIN DIST) (setq DISTMIN 0.0))
     )
     (if (= DISTMIN DIST)
      (setq LAYERFLAG nil)
      (setq LAYERFLAG T)
     )
     (setq STEP 0.0)
     (while (or (= STEP 0.0) (= STEP nil))
      (setq TMP (getdist "\nEnter step size <10.0> : "))
      (if (= nil TMP)
       (setq STEP 10.0)
       (setq STEP TMP)
      )
     )
     (setq RFL:ALIGNLIST nil RFL:PVILIST nil RFL:SUPERLIST nil)
     (if (= nil 3DPFLAG)
      (progn
       (setq ENT (car (entsel "Select RAB alignment control block (or <Return> for 2D sightlines) : ")))
       (if (/= nil ENT)
        (progn
         (RFL:RALIGNB ENT)
         (RFL:RPROFB ENT)
         (RFL:RSUPERB ENT)
        )
       )
      )
      (progn
       (setq STA 0.0)
       (setq RFL:ALIGNLIST nil)
       (setq ENT (entnext 3DPFLAG))
       (setq ENTLIST (entget ENT))
       (setq P1 (cdr (assoc 10 ENTLIST)))
       (setq Z1 (caddr P1))
       (setq P1 (list (car P1) (cadr P1)))
       (setq RFL:PVILIST (list (list STA Z1 "L" 0.0)))
       (while (= "VERTEX" (cdr (assoc 0 ENTLIST)))
        (setq ENT (entnext ENT))
        (setq ENTLIST (entget ENT))
        (if (= "VERTEX" (cdr (assoc 0 ENTLIST)))
         (progn
          (setq P2 (cdr (assoc 10 ENTLIST)))
          (setq Z2 (caddr P2))
          (setq P2 (list (car P2) (cadr P2)))
          (setq RFL:ALIGNLIST (append RFL:ALIGNLIST (list (list STA P1 P2 0.0))))
          (setq STA (+ STA (distance P1 P2)))
          (setq RFL:PVILIST (append RFL:PVILIST (list (list STA Z2 "L" 0.0))))
          (setq P1 P2)
          (setq Z1 Z2)
         )
        )
       )
       (setq RFL:SUPERLIST (list (list -1e9 0.0 0.0) (list 1e9 0.0 0.0)))
      )
     )
     (setq OBSURFACE nil)
     (setq BARRIERALLIST nil)
     (if (or (= nil RFL:ALIGNLIST) (= nil RFL:PVILIST) (= nil RFL:SUPERLIST))
      (progn
       (GETBARRIERALLIST)
       (if (= nil BARRIERALLIST)
        (progn
; Lines Only
         (DRAWLINES nil nil OBSURFACE)
        )
        (progn
; Barrier
         (DRAWLINES T nil OBSURFACE)
        )
       )
      )
      (progn
; Solve full 3D
       (setq CONTROLAL RFL:ALIGNLIST)
       (setq HEYE (getreal "\nEnter eye height <1.050> : "))
       (if (= nil HEYE) (setq HEYE 1.05))
       (setq HTARGET (getreal "\nEnter target height <0.150> : "))
       (if (= nil HTARGET) (setq HTARGET 0.15))
       (initget "Yes No")
       (if (= "Yes" (getkword "\nCompare lines to surface (Yes/<No>) : "))
        (progn
         (setq OBSURFACE (RFL:GETC3DSURFACE))
        )
       )
       (GETBARRIERALLIST)
       (if (= nil BARRIERALLIST)
        (progn
         (DRAWLINES nil T OBSURFACE)
        )
        (progn
         (DRAWLINES T T OBSURFACE)
        )
       )
      )
     )
    )
   )
  )
 )

 (setvar "CMDECHO" CMDECHO)
 (setvar "ANGBASE" ANGBASE)
 (setvar "ANGDIR" ANGDIR)
 (setvar "OSMODE" OSMODE)
 (setvar "CECOLOR" CECOLOR)
 (setvar "CLAYER" CLAYER)
 (setq RFL:ALIGNLIST ALSAVE RFL:PVILIST PVISAVE RFL:SUPERLIST ESAVE)
 BELOWLIST
)
