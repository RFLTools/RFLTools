;
;
;     Program written by Robert Livingston, 04-10-22
;
;     C:SIGHTLINE is a routine for drawing lines point to point along an alignment or path at a given length
;
;
(defun C:SIGHTLINE (/ *error* ALSAVE ANGBASE ANGDIR CMDECHO ENT ENT2 ENTLIST FR OS OSMODE P P1 P2 PM PREVENT
                      SIGHTDIST STA STA1 STA2 STAEND STAM STEP)
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setvar "OSMODE" 0)
 (setq ALSAVE RFL:ALIGNLIST)
 (setq PREVENT nil)

 (defun *error* (msg)
  (princ msg)
  (setvar "CMDECHO" CMDECHO)
  (setvar "ANGBASE" ANGBASE)
  (setvar "ANGDIR" ANGDIR)
  (setvar "OSMODE" OSMODE)
  ;(setq *error* nil)
 )

 (command "._UNDO" "M")

 (if (= nil RFL:ALIGNLIST)
  (progn
   (setq ENT (entsel "\nSelect polyline : "))
   (setq P (cadr ENT)
         P (list (car P) (cadr P))
         P1 nil
         P2 nil
         ENT (car ENT)
         ENTLIST (entget ENT)
   )
   (if (= (cdr (assoc 0 ENTLIST)) "POLYLINE")
    (progn
     (command "._CONVERT" "P" "S" ENT "")
     (setq ENTLIST (entget ENT))
    )
   )
   (if (= (cdr (assoc 0 ENTLIST)) "LWPOLYLINE")
    (progn
     (setq P1 (cdr (assoc 10 ENTLIST)))
     (setq P2 (cdr (assoc 10 (reverse ENTLIST))))
     (if (< (distance P P1) (distance P P2))
      (setq P P1)
      (setq P P2)
     )
    )
   )
   (setq RFL:ALIGNLIST (RFL:ALIGNDEF ENT P 0.0))
  )
 )
 (if (= nil RFL:ALIGNLIST)
  (princ "\n!!!  No alignment defined or error selecting polyline !!!")
  (progn
   (initget "Forward Reverse")
   (setq FR (getkword "\nForward or Reverse <Forward> : "))
   (if (= nil FR) (setq FR "Forward"))
   (setq STA (getreal "\nEnter start chainage (<return> for alignment start/end) : "))
   (if (= STA nil)
    (progn
     (setq STA (caar RFL:ALIGNLIST))
     (setq STAEND STA)
     (if (= FR "Reverse")
      (setq STA (+ STA (RFL:GETALIGNLENGTH)))
      (setq STAEND (+ STAEND (RFL:GETALIGNLENGTH)))
     )
    )
   )
   (setq OS (getreal "\nOffset from centerline (-ve = left, +ve = right) <0.0> : "))
   (if (= nil OS) (setq OS 0.0))
   (setq STEP 0.0)
   (while (<= STEP 0.0) (setq STEP (getreal "\nEnter step size : ")))
   (setq SIGHTDIST 0.0)
   (while (<= SIGHTDIST 0.0) (setq SIGHTDIST (getreal "\nEnter sight distance : ")))
   (if (= FR "Reverse")
    (progn
     (setq STEP (* -1.0 STEP))
     (setq SIGHTDIST (* -1.0 SIGHTDIST))
    )
   )
   (setq STOPFLAG nil)
   (while (= STOPFLAG nil)
    (setq P (RFL:XY (list STA OS)))
    (if (/= nil P)
     (progn
      (setq STA1 (+ STA STEP))
      (setq P1 (RFL:XY (list STA1 OS)))
      (while (/= nil P1)
       (setq STA2 (+ STA1 STEP))
       (if (= FR "Forward")
        (setq STA2 (min STAEND STA2))
        (setq STA2 (max STAEND STA2))
       )
       (setq P2 (RFL:XY (list STA2 OS)))
       (if (/= P2 nil)
        (if (> (distance P P2) (abs SIGHTDIST))
         (progn
          (while (> (abs (- STA1 STA2)) RFL:TOL)
           (setq STAM (/ (+ STA1 STA2) 2.0))
           (setq PM (RFL:XY (list STAM OS)))
           (if (< (abs SIGHTDIST) (distance P PM))
            (setq STA2 STAM P2 PM)
            (setq STA1 STAM P1 PM)
           )
          )
          (entmake (list (cons 0 "LINE")
                         (append (list 10) P (list 0.0))
                         (append (list 11) PM (list 0.0))
                   )
          )
          (setq ENT (entlast))
          (RFL:PUTPREVENT ENT PREVENT)(RFL:PUTNEXTENT PREVENT ENT)(setq PREVENT ENT)
          (setq P1 nil)
         )
        )
       )
       (if (/= P1 nil)
        (progn
         (setq STA1 (+ STA1 STEP))
         (setq P1 (RFL:XY (list STA1 OS)))
        )
       )
      )
     )
    )
    (setq STA (+ STA STEP))
    (if (= FR "Forward")
     (if (> STA STAEND) (setq STOPFLAG T))
     (if (< STA STAEND) (setq STOPFLAG T))
    )
   )
  )
 )

 (setvar "CMDECHO" CMDECHO)
 (setvar "ANGBASE" ANGBASE)
 (setvar "ANGDIR" ANGDIR)
 (setvar "OSMODE" OSMODE)
 (setq RFL:ALIGNLIST ALSAVE)
 nil
)
