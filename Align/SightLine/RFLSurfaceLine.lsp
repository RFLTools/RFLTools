;
;
;     Program written by Robert Livingston 2013-02-12
;
;     RFL:SURFACELINE returns a list of surface points (Civil 3D) sampled from endpoints of line entity
;
;
(defun RFL:SURFACELINE (OBSURFACE ENT / BELOWFLAG C CECOLOR CENT CLAYER COLORA COLORB ELEVL ENTLIST H H1 H2 LTOTAL L1 L2 LAYERA LAYERB OBSURFACE OGLINE OGLINELIST OGOFFSETLIST OSMODE ORTHOMODE P PBASE P1 P2 POINTL PREVENT Z Z1 Z2)
 (setq PREVENT nil)
 (setq BELOWFLAG nil)
 (defun ELEVL (L LTOTAL Z1 Z2 / )
  (+ Z1 (* (/ L LTOTAL) (- Z2 Z1)))
 )
 (defun POINTL (L LTOTAL P1 P2 Z)
  (list (+ (car P1) (* (/ L LTOTAL) (- (car P2) (car P1))))
        (+ (cadr P1) (* (/ L LTOTAL) (- (cadr P2) (cadr P1))))
        Z
  )
 )
 (setq OSMODE (getvar "OSMODE"))
 (setvar "OSMODE" 0)
 (setq ORTHOMODE (getvar "ORTHOMODE"))
 (setvar "ORTHOMODE" 0)
 (setq CECOLOR (getvar "CECOLOR"))
 (setq COLORA "RGB:0,255,0")
 (setq COLORB "RGB:255,0,0")
 (setq CLAYER (getvar "CLAYER"))
 (setq LAYERA (strcat CLAYER "_ABOVE"))
 (setq LAYERB (strcat CLAYER "_BELOW"))
 (if (= nil (tblsearch "LAYER" LAYERA))
  (entmake (list (cons 0 "LAYER")
                 (cons 100 "AcDbSymbolTableRecord")
                 (cons 100 "AcDbLayerTableRecord")
                 (cons 2 LAYERA)
                 (cons 62 -7)
                 (cons 70 0)
           )
  )
 )
 (if (= nil (tblsearch "LAYER" LAYERB))
  (entmake (list (cons 0 "LAYER")
                 (cons 100 "AcDbSymbolTableRecord")
                 (cons 100 "AcDbLayerTableRecord")
                 (cons 2 LAYERB)
                 (cons 62 -7)
                 (cons 70 0)
           )
  )
 )
 (setq OGLINE nil)
 (setq OGLINELIST nil)
 (setq OGOFFSETLIST nil)
 (if (/= nil ENT) (setq ENTLIST (entget ENT)))
 (if (and (/= nil OBSURFACE) (= "LINE" (cdr (assoc 0 ENTLIST))))
  (progn
   (setq P1 (cdr (assoc 10 ENTLIST)))
   (setq P2 (cdr (assoc 11 ENTLIST)))
   (setq OGLINE (vlax-invoke-method OBSURFACE "SampleElevations" (car P1) (cadr p1) (car P2) (cadr p2)))
   (if (/= nil OGLINE)
    (if (/= 0 (vlax-variant-type OGLINE))
     (progn
      (setq OGLINELIST nil)
      (setq OGLINE (vlax-variant-value OGLINE))
      (setq C (vlax-safearray-get-l-bound OGLINE 1))
      (while (<= C (vlax-safearray-get-u-bound OGLINE 1))
       (setq OGLINELIST (append OGLINELIST (list (list (vlax-safearray-get-element OGLINE C)
                                                       (vlax-safearray-get-element OGLINE (+ C 1))
                                                       (vlax-safearray-get-element OGLINE (+ C 2))
                                                 )
                                           )
                        )
       )
       (setq C (+ C 3))
      )
      (setq C 0)
      (while (< C (length OGLINELIST))
       (setq P (nth C OGLINELIST))
       (setq P (list (car P) (cadr P)))
       (setq OGOFFSETLIST (append OGOFFSETLIST
                                  (list (list (distance (list (car P1) (cadr P1)) P)
                                              (last (nth C OGLINELIST))
                                        )
                                  )
                          )
       )
       (setq C (+ C 1))
      )
     )
    )
   )
  )
 )
 (if (/= nil OGOFFSETLIST)
  (progn
   (setq C 1)
   (setq Z1 (caddr P1))
   (setq P1 (list (car P1) (cadr P1)))
   (setq Z2 (caddr P2))
   (setq P2 (list (car P2) (cadr P2)))
   (setq LTOTAL (distance P1 P2))
   (setq PBASE (list 0 Z1))
   (while (< C (length OGOFFSETLIST))
    (if (/= nil (setq P (inters (list 0 Z1)
                                (list LTOTAL Z2)
                                (nth (- C 1) OGOFFSETLIST)
                                (nth C OGOFFSETLIST))))
     (progn
      (if (> (ELEVL (car (nth (- C 1) OGOFFSETLIST)) LTOTAL Z1 Z2) (cadr (nth (- C 1) OGOFFSETLIST)))
       (progn
        (setvar "CECOLOR" COLORA)
        (setvar "CLAYER" LAYERA)
       )
       (progn
        (setq BELOWFLAG T)
        (setvar "CECOLOR" COLORB)
        (setvar "CLAYER" LAYERB)
       )
      )
      (entmake (list (cons 0 "LINE")
                     (append (list 10) (POINTL (car PBASE) LTOTAL P1 P2 (cadr PBASE)))
                     (append (list 11) (POINTL (car P) LTOTAL P1 P2 (cadr P)))
               )
      )
      (setq CENT (entlast))
      (RFL:PUTPREVENT CENT PREVENT)(RFL:PUTNEXTENT PREVENT CENT)(setq PREVENT CENT)
      (setq PBASE P)
     )
    )
    (setq C (+ C 1))
   )
   (if (> (ELEVL (car (last OGOFFSETLIST)) LTOTAL Z1 Z2) (cadr (last OGOFFSETLIST)))
    (progn
     (setvar "CECOLOR" COLORA)
     (setvar "CLAYER" LAYERA)
    )
    (progn
     (setq BELOWFLAG T)
     (setvar "CECOLOR" COLORB)
     (setvar "CLAYER" LAYERB)
    )
   )
   (entmake (list (cons 0 "LINE")
                  (append (list 10) (POINTL (car PBASE) LTOTAL P1 P2 (cadr PBASE)))
                  (append (list 11) (POINTL (car (last OGOFFSETLIST)) LTOTAL P1 P2 Z2))
            )
   )
   (setq CENT (entlast))
   (RFL:PUTPREVENT CENT PREVENT)(RFL:PUTNEXTENT PREVENT CENT)(setq PREVENT CENT)
  )
 )
 (setvar "CECOLOR" CECOLOR)
 (setvar "OSMODE" OSMODE)
 (setvar "ORTHOMODE" ORTHOMODE)
 (setvar "CLAYER" CLAYER)
 BELOWFLAG
)
