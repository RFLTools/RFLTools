;
;
;     Program written by Robert Livingston, 2010-12-08
;
;     CSIGHTLINEPROF is a routine for drawing lines point to point along a profile at a given length, eye height and target height
;
;
(defun C:SIGHTLINEPROF (/ *error* ANGBASE ANGDIR CMDECHO ENT EYE FR OSMODE P P1 P2 PM PREVENT
                          SIGHTDIST STA STA1 STA2 STAEND STAM STEP TARGET TMP Z)
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setvar "OSMODE" 0)
 (setq PREVENT nil)

 (defun *error* (msg)
  (princ msg)
  (setvar "CMDECHO" CMDECHO)
  (setvar "ANGBASE" ANGBASE)
  (setvar "ANGDIR" ANGDIR)
  (setvar "OSMODE" OSMODE)
  ;(setq *error* nil)
 )

 (command "._UNDO" "M")

 (RFL:PROFDEF)
 (if (= nil RFL:PVILIST)
  (princ "\n!!!  No profile defined  !!!")
  (progn
   (initget "Forward Reverse")
   (setq FR (getkword "\nForward or Reverse <Forward> : "))
   (if (= nil FR) (setq FR "Forward"))
   (setq STA (getreal "\nEnter start chainage (<return> for profile start) : "))
   (if (= STA nil)
    (setq STA (caar RFL:PVILIST))
   )
   (setq STAEND (getreal "\nEnter end chainage (<return> for profile end) : "))
   (if (= STAEND nil)
    (setq STAEND (car (last RFL:PVILIST)))
   )
   (if (= FR "Reverse")
    (progn
     (setq TMP STA)
     (setq STA STAEND)
     (setq STAEND TMP)
    )
   )
   (setq EYE (getreal "\nEye height (<return> = 1.05) : "))
   (if (= nil EYE) (setq EYE 1.05))
   (setq TARGET (getreal "\nTarget height (<return> = 0.38) : "))
   (if (= nil TARGET) (setq TARGET 0.38))
   (setq STEP 0.0)
   (while (<= STEP 0.0) (setq STEP (getreal "\nEnter step size : ")))
   (setq SIGHTDIST 0.0)
   (while (<= SIGHTDIST 0.0) (setq SIGHTDIST (getreal "\nEnter sight distance : ")))
   (if (= FR "Reverse")
    (progn
     (setq STEP (* -1.0 STEP))
     (setq SIGHTDIST (* -1.0 SIGHTDIST))
    )
   )
   (setq STOPFLAG nil)
   (while (= STOPFLAG nil)
    (setq Z (RFL:ELEVATION STA))
    (if (/= nil Z)
     (progn
      (setq P1 (RFL:PROFPOINT STA (+ Z EYE)))
      (setq Z (RFL:ELEVATION (+ STA SIGHTDIST)))
      (if (/= nil Z)
       (progn
        (setq P2 (RFL:PROFPOINT (+ STA SIGHTDIST) (+ Z TARGET)))
        (entmake (list (cons 0 "LINE")
                       (append (list 10) P1)
                       (append (list 11) P2)
                 )
        )
        (setq ENT (entlast))
        (RFL:PUTPREVENT ENT PREVENT)(RFL:PUTNEXTENT PREVENT ENT)(setq PREVENT ENT)
       )
      )
     )
    )
    (setq STA (+ STA STEP))
    (if (= FR "Forward")
     (if (> STA STAEND) (setq STOPFLAG T))
     (if (< STA STAEND) (setq STOPFLAG T))
    )
   )
  )
 )

 (setvar "CMDECHO" CMDECHO)
 (setvar "ANGBASE" ANGBASE)
 (setvar "ANGDIR" ANGDIR)
 (setvar "OSMODE" OSMODE)
)
