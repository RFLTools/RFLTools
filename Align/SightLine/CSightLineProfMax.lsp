;
;
;     Program written by Robert Livingston, 13-03-26
;
;     C:SIGHTLINEPROFMAX is a routine for finding the longest point to point sightline along a profile
;
;
(defun C:SIGHTLINEPROFMAX (/ *error* ANGBASE ANGDIR CHECKELEVATIONS C C1 C2 CMDECHO CONTINUEFLAG ELEVLIST ENT EYE FR OSMODE OUTFILE
                             P P1 P2 PINWHEEL PM PREVENT SIGHTDIST SIGHTDISTMIN STA STA1 STA2 STAEND STASTART STEP STEPCHECK
                             TARGET TMP Z Z1 Z2)
;(defun C:SIGHTLINEPROFMAX ()
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setvar "OSMODE" 0)

 (setq PREVENT nil)
 
 (defun *error* (msg)
  (princ msg)
  (close OUTFILE)
  (setvar "CMDECHO" CMDECHO)
  (setvar "ANGBASE" ANGBASE)
  (setvar "ANGDIR" ANGDIR)
  (setvar "OSMODE" OSMODE)
  ;(setq *error* nil)
 )

 (defun PINWHEEL ()
  (if (= PINWHEELCH nil)
   (setq PINWHEELCH "|")
  )
  (setq PINWHEELCH (cond ((= PINWHEELCH "|") "/")
                         ((= PINWHEELCH "/") "-")
                         ((= PINWHEELCH "-") "\\")
                         ((= PINWHEELCH "\\") "|")))
  (princ "\r")
  (princ PINWHEELCH)
 )

 (defun CHECKELEVATIONS (/ C DELTA Z Z1 Z2)
  (setq RES T)
  (setq Z1 (+ (cadr (nth C1 ELEVLIST)) EYE))
  (setq Z2 (+ (cadr (nth C2 ELEVLIST)) TARGET))
  (setq DELTA (/ (- Z2 Z1) (- C2 C1)))
  (setq C (+ C1 1))
  (while (and RES (< C C2))
   (setq Z (+ Z1 (* (- C C1) DELTA)))
   (if (< Z (cadr (nth C ELEVLIST))) (setq RES nil))
   (setq C (+ C 1))
  )
  (eval RES)
 )
 
 (command "._UNDO" "M")

 (setq SIGHTDISTMIN nil)
 (setq ELEVLIST nil)
 
 (if (= nil RFL:PVILIST)
  (princ "\n!!!  No profile defined  !!!")
  (progn
   (RFL:PROFDEF)
   (initget "Forward Reverse")
   (setq FR (getkword "\nForward or Reverse <Forward> : "))
   (if (= nil FR) (setq FR "Forward"))
   (setq STASTART (getreal "\nEnter start chainage (<return> for profile start) : "))
   (if (= STASTART nil)
    (setq STASTART (caar RFL:PVILIST))
   )
   (setq STAEND (getreal "\nEnter end chainage (<return> for profile end) : "))
   (if (= STAEND nil)
    (setq STAEND (car (last RFL:PVILIST)))
   )
   (setq EYE (getreal "\nEye height (<return> = 1.05) : "))
   (if (= nil EYE) (setq EYE 1.05))
   (setq TARGET (getreal "\nTarget height (<return> = 0.38) : "))
   (if (= nil TARGET) (setq TARGET 0.38))
   (setq STEP (getreal "\nEnter step size (<return> = 5.0) : "))
   (if (= nil STEP) (setq STEP 5.0))
;   (setq STEPCHECK (getreal "\nEnter check step size (<return> = 1.0) : "))
;   (if (= nil STEPCHECK) (setq STEPCHECK 1.0))
   (setq STEPCHECK (/ STEP 10.0))
   (setq SIGHTDIST (getreal "\nEnter maximum sight distance for checking (<return> = 250.0) : "))
   (if (= nil SIGHTDIST) (setq SIGHTDIST 250.0))
   (princ (strcat "\nSight distances stored in : " (getenv "UserProfile") "\\Documents\\" "SIGHTLINEPROFMAX.CSV\n"))
   (setq OUTFILE (open (strcat (getenv "UserProfile") "\\Documents\\" "SIGHTLINEPROFMAX.CSV") "w"))
   (princ "Computing ground/design elevations.")
   (setq STA STASTART)
   (while (<= STA STAEND)
    (PINWHEEL)
    (setq Z (RFL:ELEVATION STA))
    (if (/= nil Z)
     (setq ELEVLIST (append ELEVLIST (list (list STA Z))))
    )
    (setq STA (+ STA STEPCHECK))
   )
   (princ "\n")
   (if (= FR "Reverse") (setq ELEVLIST (reverse ELEVLIST)))
   (setq C1 0)
   (while (< (+ C1 1) (length ELEVLIST))
    (setq C2 (+ C1 1))
    (setq Z1 (cadr (nth C1 ELEVLIST)))
    (setq Z2 (cadr (nth C2 ELEVLIST)))
    (setq CONTINUEFLAG T)
    (while (and (CHECKELEVATIONS) CONTINUEFLAG (<= (abs (- (car (nth C2 ELEVLIST)) (car (nth C1 ELEVLIST)))) SIGHTDIST))
     (PINWHEEL)
     (setq C2 (+ C2 1))
     (if (= C2 (length ELEVLIST)) (setq CONTINUEFLAG nil))
    )
    (setq C2 (- C2 1))
    (if CONTINUEFLAG
     (progn
      (setq P1 (RFL:PROFPOINT (car (nth C1 ELEVLIST)) (+ (cadr (nth C1 ELEVLIST)) EYE)))
      (setq P2 (RFL:PROFPOINT (car (nth C2 ELEVLIST)) (+ (cadr (nth C2 ELEVLIST)) TARGET)))
      (entmake (list (cons 0 "LINE")
                     (append (list 10) (list (car P1) (cadr P1) 0.0))
                     (append (list 11) (list (car P2) (cadr P2) 0.0))
               )
      )
      (setq ENT (entlast))
      (RFL:PUTPREVENT ENT PREVENT)(RFL:PUTNEXTENT PREVENT ENT)(setq PREVENT ENT)
      (princ (strcat (rtos (car (nth C1 ELEVLIST)) 2 8) "," (rtos (abs (- (car (nth C2 ELEVLIST)) (car (nth C1 ELEVLIST)))) 2 8) "\n") OUTFILE)
      (if (= nil SIGHTDISTMIN)
       (setq SIGHTDISTMIN (abs (- (car (nth C2 ELEVLIST)) (car (nth C1 ELEVLIST)))))
       (if (< (abs (- (car (nth C2 ELEVLIST)) (car (nth C1 ELEVLIST)))) SIGHTDISTMIN)
        (setq SIGHTDISTMIN (abs (- (car (nth C2 ELEVLIST)) (car (nth C1 ELEVLIST)))))
       )
      )
     )
     (progn
     )
    )
    (setq C1 (+ C1 10))
   )
  )
 )
; (alert (strcat "Minimum sight distance = " (rtos SIGHTDISTMIN 2 1)))
 
 (close OUTFILE)
 (setvar "CMDECHO" CMDECHO)
 (setvar "ANGBASE" ANGBASE)
 (setvar "ANGDIR" ANGDIR)
 (setvar "OSMODE" OSMODE)
)
