;
;
;    Program Written by Robert Livingston, 99/07/14
;    RFL:FITSPIRALLA Fits a reverse engineered DCA spiral between a line and an arc
;
;    Revised 2026-10-14 (Hermes):
;      * the two candidate spirals are now built as +/- K along the line from the
;        perpendicular foot.  The old code went K "toward P1" and "toward P2",
;        which is the same thing only while the foot lies BETWEEN P1 and P2; when
;        the foot falls outside the line both candidates collapse onto the same
;        point and one of them is a spiral that misses the arc entirely,
;      * a candidate whose tangency point does not land on the arc is rejected,
;      * a candidate that would have to EXTEND the line past one of its own ends
;        is rejected in favour of the other; when both are usable the original
;        rule is kept, so ordinary cases behave exactly as before.
;
(defun RFL:FITSPIRALLA (ENT1 ENT2 / A ANG ANG1 ANG2 ANG3 B C D1 D2 D3 DIR ENTLIST1 ENTLIST2
                                    G1 G2 K OK1 OK2 ON1 ON2 P P1 P2 PC PC1 PC2 PP PLT PLT1 PLT2
                                    PLTST PLTST1 PLTST2 PST PST1 PST2 R THETA THETA1 THETA2
                                    T1 T2 USESOL1 UUX UUY)
 (setq ENTLIST1 (entget ENT1))
 (setq ENTLIST2 (entget ENT2))
 (setq P1 (cdr (assoc 10 ENTLIST1)))
 (setq P1 (list (car P1) (cadr P1)))
 (setq P2 (cdr (assoc 11 ENTLIST1)))
 (setq P2 (list (car P2) (cadr P2)))
 (setq PC (cdr (assoc 10 ENTLIST2)))
 (setq PC (list (car PC) (cadr PC)))
 (setq R (cdr (assoc 40 ENTLIST2)))
 (setq ANG1 (cdr (assoc 50 ENTLIST2)))
 (setq PC1 (list (+ (car PC) (* R (cos ANG1)))
                 (+ (cadr PC) (* R (sin ANG1)))))
 (setq ANG2 (cdr (assoc 51 ENTLIST2)))
 (setq PC2 (list (+ (car PC) (* R (cos ANG2)))
                 (+ (cadr PC) (* R (sin ANG2)))))
 (if (> (sin (- (angle P1 PC) (angle P1 P2))) 0.0)
  (setq DIR 1.0)
  (setq DIR -1.0)
 )
 (setq D1 (distance P1 PC))
 (setq D2 (distance P2 PC))
 (setq D3 (distance P1 P2))
 (setq A (/ (+ (- (expt D1 2) (expt D2 2)) (expt D3 2)) (* 2 D3)))
 (setq B (/ (+ (- (expt D2 2) (expt D1 2)) (expt D3 2)) (* 2 D3)))
 (setq C (sqrt (- (expt D1 2) (expt A 2))))
 (if (> A B)
  (setq PP (list (+ (car P1) (* (/ A D3) (- (car P2) (car P1))))
                 (+ (cadr P1) (* (/ A D3) (- (cadr P2) (cadr P1))))
           )
  )
  (setq PP (list (+ (car P2) (* (/ B D3) (- (car P1) (car P2))))
                 (+ (cadr P2) (* (/ B D3) (- (cadr P1) (cadr P2))))
           )
  )
 )
 (if (< (distance PP P1) RFL:TOLFINE)
  (setq P1 (list (+ (car P2) (* 0.9 (- (car P1) (car P2))))
                 (+ (cadr P2) (* 0.9 (- (cadr P1) (cadr P2))))))
 )
 (if (< (distance PP P2) RFL:TOLFINE)
  (setq P2 (list (+ (car P1) (* 0.9 (- (car P2) (car P1))))
                 (+ (cadr P1) (* 0.9 (- (cadr P2) (cadr P1))))))
 )
 (if (< C R)
  (princ "\nRFL:FITSPIRALLA - the line passes inside the arc, no spiral is possible.")
  (progn
   (setq P (- C R))
   (setq THETA1 0.0)
   (setq THETA2 pi)
   (setq THETA (/ (+ THETA1 THETA2) 2.0))
   (while (> (abs (- THETA2 THETA1)) RFL:TOLFINE)
    (if (< (RFL:SPIRALPR THETA) (/ P R))
     (setq THETA1 THETA)
     (setq THETA2 THETA)
    )
    (setq THETA (/ (+ THETA1 THETA2) 2.0))
   )
   (setq K (* R (RFL:SPIRALKR THETA)))
   (setq UUX (cos (angle P1 P2)) UUY (sin (angle P1 P2)))
   ;; the tangency point sits K behind the foot, looking along the line
   (setq PLT1 (list (- (car PP) (* K UUX))
                    (- (cadr PP) (* K UUY))))
   (setq PLTST1 (list (+ (car PLT1)
                         (* R (- (RFL:SPIRALFXR THETA) (/ (RFL:SPIRALFYR THETA) (RFL:TAN THETA))) (cos (angle P1 P2)))
                      )
                      (+ (cadr PLT1)
                         (* R (- (RFL:SPIRALFXR THETA) (/ (RFL:SPIRALFYR THETA) (RFL:TAN THETA))) (sin (angle P1 P2)))
                      )
                )
   )
   (setq PST1 (list (+ (car PLT1)
                       (* R (RFL:SPIRALFXR THETA) (cos (angle P1 P2)))
                       (* -1.0 DIR R (RFL:SPIRALFYR THETA) (sin (angle P1 P2)))
                    )
                    (+ (cadr PLT1)
                       (* R (RFL:SPIRALFXR THETA) (sin (angle P1 P2)))
                       (* DIR R (RFL:SPIRALFYR THETA) (cos (angle P1 P2)))
                    )
              )
   )
   (setq PLT2 (list (+ (car PP) (* K UUX))
                    (+ (cadr PP) (* K UUY))))
   (setq PLTST2 (list (+ (car PLT2)
                         (* R (- (RFL:SPIRALFXR THETA) (/ (RFL:SPIRALFYR THETA) (RFL:TAN THETA))) (cos (angle P2 P1)))
                      )
                      (+ (cadr PLT2)
                         (* R (- (RFL:SPIRALFXR THETA) (/ (RFL:SPIRALFYR THETA) (RFL:TAN THETA))) (sin (angle P2 P1)))
                      )
                )
   )
   (setq PST2 (list (+ (car PLT2)
                       (* R (RFL:SPIRALFXR THETA) (cos (angle P2 P1)))
                       (* DIR R (RFL:SPIRALFYR THETA) (sin (angle P2 P1)))
                    )
                    (+ (cadr PLT2)
                       (* R (RFL:SPIRALFXR THETA) (sin (angle P2 P1)))
                       (* -1.0 DIR R (RFL:SPIRALFYR THETA) (cos (angle P2 P1)))
                    )
              )
   )
   ;; a usable candidate must land on the arc, and must not need the line extended
   (setq OK1 (< (abs (- (distance PC PST1) R)) (* R RFL:TOL)))
   (setq OK2 (< (abs (- (distance PC PST2) R)) (* R RFL:TOL)))
   (setq T1 (+ (* (- (car PLT1) (car P1)) UUX) (* (- (cadr PLT1) (cadr P1)) UUY)))
   (setq T2 (+ (* (- (car PLT2) (car P1)) UUX) (* (- (cadr PLT2) (cadr P1)) UUY)))
   (setq ON1 (and (> T1 (- (* D3 RFL:TOL))) (< T1 (+ D3 (* D3 RFL:TOL)))))
   (setq ON2 (and (> T2 (- (* D3 RFL:TOL))) (< T2 (+ D3 (* D3 RFL:TOL)))))
   (if (and (not OK1) (not OK2))
    (princ "\nRFL:FITSPIRALLA - no spiral tangency point lands on the arc.")
    (progn
     (cond
      ((not OK1) (setq USESOL1 nil))
      ((not OK2) (setq USESOL1 T))
      ((and ON1 (not ON2)) (setq USESOL1 T))
      ((and ON2 (not ON1)) (setq USESOL1 nil))
      (T
       (if (= DIR 1.0)
        (setq USESOL1 (< (RFL:ANGLE3P PST1 PC PC1) (RFL:ANGLE3P PST1 PC PC2)))
        (setq USESOL1 (> (RFL:ANGLE3P PST1 PC PC1) (RFL:ANGLE3P PST1 PC PC2)))
       )
      )
     )
     (if (= DIR 1.0)
      (setq G1 50 G2 51)
      (setq G1 51 G2 50)
     )
     (if USESOL1
      (progn
       (RFL:DRAWSPIRAL PLT1 PLTST1 PST1 0.0 0.0)
       (setq ENTLIST1 (subst (list 11 (car PLT1) (cadr PLT1))
                             (assoc 11 ENTLIST1)
                             ENTLIST1))
       (entmod ENTLIST1)
       (entupd ENT1)
       (setq ENTLIST2 (subst (cons G1 (angle PC PST1))
                             (assoc G1 ENTLIST2)
                             ENTLIST2))
       (entmod ENTLIST2)
       (entupd ENT2)
      )
      (progn
       (RFL:DRAWSPIRAL PLT2 PLTST2 PST2 0.0 0.0)
       (setq ENTLIST1 (subst (list 10 (car PLT2) (cadr PLT2))
                             (assoc 10 ENTLIST1)
                             ENTLIST1))
       (entmod ENTLIST1)
       (entupd ENT1)
       (setq ENTLIST2 (subst (cons G2 (angle PC PST2))
                             (assoc G2 ENTLIST2)
                             ENTLIST2))
       (entmod ENTLIST2)
       (entupd ENT2)
      )
     )
    )
   )
  )
 )
)
