;
;
;     Program written by Robert Livingston, 02/05/08
;
;     VCSTAN draws a tangent at the specified slope on a vertical curve
;
(defun C:VCSTAN (/ *error* ANGBASE ANGDIR A B C CMDECHO G G1 G2 L OSMODE P P1 P2 P3 S X X1 X2 X3 Y Y1 Y2 Y3 VEXAG)
 (setq CMDECHO (getvar "CMDECHO"))
 (setvar "CMDECHO" 0)
 (setq OSMODE (getvar "OSMODE"))
 (setvar "OSMODE" 0)
 (setq ANGBASE (getvar "ANGBASE"))
 (setvar "ANGBASE" 0.0)
 (setq ANGDIR (getvar "ANGDIR"))
 (setvar "ANGDIR" 0)

 (defun *error* (msg)
  (if (>= (atof (getvar "ACADVER")) 18.2)
   (command-s "._UCS" "P")
   (command "._UCS" "P")
  )
  (setvar "ANGBASE" ANGBASE)
  (setvar "ANGDIR" ANGDIR)
  (setvar "CMDECHO" CMDECHO)
  (setvar "OSMODE" OSMODE)
  ;(setq *error* nil)
  (print msg)
 )

 (command "._UCS" "W")
 (command "._UNDO" "M")

 (setq PLIST (RFL:GETVCURVE3P))
 (setq P1 (car PLIST) P2 (cadr PLIST) P3 (caddr PLIST) VEXAG (cadddr PLIST))

 (if (and (/= nil P1) (/= nil P2) (/= nil P3))
  (progn
   (if (= VEXAG nil)
    (progn
     (setq VEXAG (getreal (strcat "\nEnter vertical exageration (" (rtos 10.0) ") : ")))
     (if (= nil VEXAG) (setq VEXAG 10.0))
    )
   )
   (if (= nil VEXAG) (setq VEXAG 10.0))
   (setq X1 (nth 0 P1))
   (setq Y1 (/ (nth 1 P1) VEXAG))
   (setq X2 (nth 0 P2))
   (setq Y2 (/ (nth 1 P2) VEXAG))
   (setq X3 (nth 0 P3))
   (setq Y3 (/ (nth 1 P3) VEXAG))
   (setq G1 (/ (- Y2 Y1) (- X2 X1)))
   (setq G2 (/ (- Y3 Y2) (- X3 X2)))
   (setq G (getreal (strcat "\nG1 = " (rtos (* G1 100.0)) ", G2 = " (rtos (* G2 100.0)) ", enter slope (%) : ")))
   (if (/= G nil)
    (progn
     (setq G (/ G 100.0))
     (setq A (/ (- G2 G1) (- X3 X1) 2.0))
     (setq B (/ (- G2 (* G1 (/ X3 X1))) (- 1.0 (/ X3 X1))))
     (setq C (- Y1 (+ (* A X1 X1) (* B X1))))
     (setq X (+ X1 (* (/ (- G G1) (- G2 G1)) (- X3 X1))))
     (setq Y (+ (* A X X) (* B X) C))
     (setq L (getdist (strcat "\nEnter length (" (rtos (abs (- X3 X1))) ") : ")))
     (if (= nil L) (setq L (abs (- X3 X1))))
     (setq P1 (list (- X (/ L 2.0))
                    (* (- Y (* (/ L 2.0) G)) VEXAG)))
     (setq P2 (list (+ X (/ L 2.0))
                    (* (+ Y (* (/ L 2.0) G)) VEXAG)))
     (command "._LINE" P1 P2 "")
    )
   )
  )
 )

 (command "._UCS" "P")
 (setvar "ANGBASE" ANGBASE)
 (setvar "ANGDIR" ANGDIR)
 (setvar "CMDECHO" CMDECHO)
 (setvar "OSMODE" OSMODE)
)
