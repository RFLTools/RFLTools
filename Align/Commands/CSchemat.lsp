;
;
;     Program written by Robert Livingston 05/12/02
;
;     SCHEMAT draws a shcematical representation of an alignment
;
;
;     TT = Tangent Tangent label, TS = Tangent Spiral label etc...
;     AZON = Label Azimuth flag, 1 = ON, 0 = OFF
;     NEON = Label Northing/Easting flag, 1 = ON, 0 = OFF
;     ARCH = Schemat curve offset height
;     TEXTH = Text height when current text style height = 0.0
(setq RFL:SCHEMATLIST (list (cons "TT" "P.I.")
                            (cons "TS" "T.S.")
                            (cons "TA" "P.C.")
                            (cons "ST" "S.T.")
                            (cons "SS" "S.C./C.S.")
                            (cons "SA" "S.C.")
                            (cons "AT" "P.T.")
                            (cons "AS" "C.S.")
                            (cons "AA" "P.C.C.")
                            (cons "AZON" 1)
                            (cons "NEON" 0)
                            (cons "ARCH" 5.0)
                            (cons "TEXTH" 2.5)
                  )
)
(defun C:SCHEMATSETUP (/ REP TT TS TA ST SS SA AT AS AA AZON NEON ARCH TEXTH)
 (setq TT (cdr (assoc "TT" RFL:SCHEMATLIST)))
 (setq REP (getstring (strcat "\nTangent-Tangent label <" TT "> : ")))
 (if (/= "" REP) (setq TT REP))
 (setq TS (cdr (assoc "TS" RFL:SCHEMATLIST)))
 (setq REP (getstring (strcat "\nTangent-Spiral label <" TS "> : ")))
 (if (/= "" REP) (setq TS REP))
 (setq TA (cdr (assoc "TA" RFL:SCHEMATLIST)))
 (setq REP (getstring (strcat "\nTangent-Arc label <" TA "> : ")))
 (if (/= "" REP) (setq TA REP))
 (setq ST (cdr (assoc "ST" RFL:SCHEMATLIST)))
 (setq REP (getstring (strcat "\nSpiral-Tangent label <" ST "> : ")))
 (if (/= "" REP) (setq ST REP))
 (setq SS (cdr (assoc "SS" RFL:SCHEMATLIST)))
 (setq REP (getstring (strcat "\nSpiral-Spiral label <" SS "> : ")))
 (if (/= "" REP) (setq SS REP))
 (setq SA (cdr (assoc "SA" RFL:SCHEMATLIST)))
 (setq REP (getstring (strcat "\nSpiral-Arc label <" SA "> : ")))
 (if (/= "" REP) (setq SA REP))
 (setq AT (cdr (assoc "AT" RFL:SCHEMATLIST)))
 (setq REP (getstring (strcat "\nArc-Tangent label <" AT "> : ")))
 (if (/= "" REP) (setq AT REP))
 (setq AS (cdr (assoc "AS" RFL:SCHEMATLIST)))
 (setq REP (getstring (strcat "\nArc-Spiral label <" AS "> : ")))
 (if (/= "" REP) (setq AS REP))
 (setq AA (cdr (assoc "AA" RFL:SCHEMATLIST)))
 (setq REP (getstring (strcat "\nArc-Arc label <" AA "> : ")))
 (if (/= "" REP) (setq AA REP))
 (setq AZON (cdr (assoc "AZON" RFL:SCHEMATLIST)))
 (initget "OFF ON")
 (setq REP (getkword (strcat "\nLabel Azimuths (ON/OFF), <" (if (= AZON 0) "OFF" "ON") "> : ")))
 (if (/= nil REP) (if (= "OFF" REP) (setq AZON 0) (setq AZON 1)))
 (setq NEON (cdr (assoc "NEON" RFL:SCHEMATLIST)))
 (initget "OFF ON")
 (setq REP (getkword (strcat "\nLabel Northings/Eastings (ON/OFF), <" (if (= NEON 0) "OFF" "ON") "> : ")))
 (if (/= nil REP) (if (= "OFF" REP) (setq NEON 0) (setq NEON 1)))
 (setq REP 0.0)
 (while (and (/= nil REP) (<= REP 0.0))
  (setq ARCH (cdr (assoc "ARCH" RFL:SCHEMATLIST)))
  (setq REP (getdist (strcat "\nSchemat offset height, <" (rtos ARCH) "> : ")))
  (if (/= nil REP) (if (<= REP 0.0) (princ "\nMust be greater than zero!") (setq ARCH REP)))
 )
 (setq REP 0.0)
 (while (and (/= nil REP) (<= REP 0.0))
  (setq TEXTH (cdr (assoc "TEXTH" RFL:SCHEMATLIST)))
  (setq REP (getdist (strcat "\nText height, <" (rtos TEXTH) "> : ")))
  (if (/= nil REP) (if (<= REP 0.0) (princ "\nMust be greater than zero!") (setq TEXTH REP)))
 )

 (setq RFL:SCHEMATLIST (list (cons "TT" TT)
                             (cons "TS" TS)
                             (cons "TA" TA)
                             (cons "ST" ST)
                             (cons "SS" SS)
                             (cons "SA" SA)
                             (cons "AT" AT)
                             (cons "AS" AS)
                             (cons "AA" AA)
                             (cons "AZON" AZON)
                             (cons "NEON" NEON)
                             (cons "ARCH" ARCH)
                             (cons "TEXTH" TEXTH)
                       )
 )
)

(defun C:SCHEMAT (/ *error* AL ALIGNLIST ANGBASE ANGDIR ATTREQ CHECKCURVE CMDECHO CURVEPI DIMZIN FLAG FR
                    GETCODE GETCURVE GETLENGTH GETRADIUS GETTANGENT LABELLINE N1 N2 NODE NODENEXT NODEPREV
                    OSMODE P P1 P2 PBASE R REP REPD RNEXT SIGN SPIRALPI STA STABASE TIN TOUT)
 (setq ALIGNLIST RFL:ALIGNLIST)
 (setq CMDECHO (getvar "CMDECHO"))
 (setvar "CMDECHO" 0)
 (setq CLAYER (getvar "CLAYER"))
 (setq DIMZIN (getvar "DIMZIN"))
 (setvar "DIMZIN" 0)
 (setq OSMODE (getvar "OSMODE"))
 (setvar "OSMODE" 0)
 (setq ATTREQ (getvar "ATTREQ"))
 (setq ANGBASE (getvar "ANGBASE"))
 (setvar "ANGBASE" 0.0)
 (setq ANGDIR (getvar "ANGDIR"))
 (setvar "ANGDIR" 0)
 (setq TOL 5e-4)

 (command "._UNDO" "M")

 (command "._UCS" "W")

 (defun *error* (msg)
  (if (>= (atof (getvar "ACADVER")) 18.2)
   (command-s "._UCS" "P")
   (command "._UCS" "P")
  )
  (setvar "CMDECHO" CMDECHO)
  (setvar "CLAYER" CLAYER)
  (setvar "DIMZIN" DIMZIN)
  (setvar "OSMODE" OSMODE)
  (setvar "ATTREQ" ATTREQ)
  (setvar "ANGBASE" ANGBASE)
  (setvar "ANGDIR" ANGDIR)
  (alert msg)
  ;(setq *error* nil)
 )

 (defun SIGN (X)
  (if (< X 0)
   (eval -1)
   (eval 1)
  )
 )

 (defun CHECKCURVE (NODE)
  (if (= nil NODE)
   (eval nil)
   (if (listp (last NODE))
    (eval 2)
    (if (< (abs (last NODE)) TOL)
     (eval 0)
     (eval 1)
    )
   )
  )
 )

 (defun GETCURVE (NODE / A2 ATOTAL BULGE CHORD D LO LS P1 P2 R THETA THETA2)
  (if (/= nil NODE)
   (progn
    (setq BULGE (last NODE))
    (setq P1 (nth 1 NODE))
    (setq P2 (nth 2 NODE))
    (if (listp BULGE)
     (progn
      (setq LS (RFL:GETSPIRALLS2 (nth 0 BULGE) (nth 1 BULGE) (nth 2 BULGE)))
      (if (listp (last BULGE))
       (setq LO 0.0)
       (setq LO (last BULGE))
      )
      (setq THETA (RFL:GETSPIRALTHETA2 (nth 0 BULGE) (nth 1 BULGE) (nth 2 BULGE)))
      (setq R (RFL:GETSPIRALR2 (nth 0 BULGE) (nth 1 BULGE) (nth 2 BULGE)))
      (setq A2 (* 2.0 R R THETA))
      (setq THETA2 (/ (* LO LO) A2 2.0))
      (setq THETA (- THETA THETA2))
      (if (= nil S1)
       (if (= nil C1)
        (setq S1 (list THETA LS LO R))
        (setq S2 (list THETA LS LO R))
       )
       (if (= nil S2)
        (progn
         (setq S2 (list THETA LS LO R))
        )
       )
      )
     )
     (if (< (abs BULGE) TOL)
      (progn
       (setq THETA (abs (- (angle (nth 0 TOUT) (nth 1 TOUT)) (angle (nth 0 TIN) (nth 1 TIN)))))
       (if (> THETA PI) (setq THETA (- (* 2.0 PI) THETA)))
       (setq C1 (list THETA 0.0 0.0 0.0))
      )
      (progn
       (setq ATOTAL (* 4.0 (atan (abs BULGE))))
       (setq CHORD (distance P1 P2))
       (setq R (/ CHORD (* 2 (sin (/ ATOTAL 2)))))
       (setq C1 (list ATOTAL R (* R ATOTAL) (distance P1 (CURVEPI NODE))))
      )
     )
    )
   )
  )
 )

 (defun GETCODE (NODE1 NODE2 / TMP)
  (if (or (= nil NODE1) (= nil NODE2))
   (setq TMP "NONE")
   (if (listp (last NODE1))
    (if (listp (last NODE2))
     (setq TMP "S.C./C.S.")
     (if (< (abs (last NODE2)) TOL)
      (setq TMP "S.T.")
      (setq TMP "S.C.")
     )
    )
    (if (< (abs (last NODE1)) TOL)
     (if (listp (last NODE2))
      (setq TMP "T.S.")
      (if (< (abs (last NODE2)) TOL)
       (setq TMP "P.I.")
       (setq TMP "B.C.")
      )
     )
     (if (listp (last NODE2))
      (setq TMP "C.S.")
      (if (< (abs (last NODE2)) TOL)
       (setq TMP "E.C.")
       (setq TMP "P.C.C.")
      )
     )
    )
   )
  )
  (eval TMP)
 )

 (defun CURVEPI (NODE / ANG ATOTAL BULGE CHORD D P1 P2 PINT)
  (setq P1 (nth 1 NODE))
  (setq P2 (nth 2 NODE))
  (setq BULGE (last NODE))
  (setq ATOTAL (* 4.0 (atan BULGE)))
  (setq CHORD (distance P1 P2))
  (setq D (/ CHORD (* 2.0 (cos (/ ATOTAL 2.0)))))
  (setq ANG (- (angle P1 P2) (/ ATOTAL 2.0)))
  (setq PINT (list (+ (nth 0 P1) (* D (cos ANG)))
                   (+ (nth 1 P1) (* D (sin ANG)))))
 )

 (defun SPIRALPI (NODE / A2 ANG BULGE DIR LO P P1 PINT R THETA THETA2)
  (setq BULGE (last NODE))
  (if (listp (setq LO (last BULGE)))
   (setq PINT (nth 1 BULGE))
   (if (< (abs LO) TOL)
    (setq PINT (nth 1 BULGE))
    (progn
     (setq DIR (SIGN (- (angle (nth 2 BULGE) (nth 1 BULGE))
                        (angle (nth 1 BULGE) (nth 0 BULGE)))))
     (setq THETA (RFL:GETSPIRALTHETA2 (nth 0 BULGE) (nth 1 BULGE) (nth 2 BULGE)))
     (setq R (RFL:GETSPIRALR2 (nth 0 BULGE) (nth 1 BULGE) (nth 2 BULGE)))
     (setq A2 (* 2.0 R R THETA))
     (setq THETA2 (/ (* LO LO) A2 2.0))
     (setq ANG (angle (nth 0 BULGE) (nth 1 BULGE)))
     (if (< (distance (nth 2 NODE) (nth 2 BULGE)) TOL)
      (setq P1 (nth 1 NODE))
      (setq P1 (nth 2 NODE))
     )
     (setq P (list (+ (nth 0 P1) (cos (+ ANG (* DIR THETA2))))
                   (+ (nth 1 P1) (sin (+ ANG (* DIR THETA2))))))
     (setq PINT (inters (nth 1 BULGE) (nth 2 BULGE) P1 P nil))
    )
   )
  )
 )

 (defun GETTANGENT (IO NODE / P1 P2)
  (if (= nil NODE)
   (setq P1 nil P2 nil)
   (if (listp (last NODE))
    (if (= IO "IN")
     (setq P1 (nth 1 NODE) P2 (SPIRALPI NODE))
     (setq P1 (SPIRALPI NODE) P2 (nth 2 NODE))
    )
    (if (< (abs (last NODE)) TOL)
     (setq P1 (nth 1 NODE) P2 (nth 2 NODE))
     (if (= IO "IN")
      (setq P1 (nth 1 NODE) P2 (CURVEPI NODE))
      (setq P1 (CURVEPI NODE) P2 (nth 2 NODE))
     )
    )
   )
  )
  (list P1 P2)
 )

 (defun GETRADIUS (NODE / ATOTAL BULGE CHORD DIR P1 P2 R)
  (if (= nil NODE)
   (setq R 0.0 DIR 0.0)
   (progn
    (setq P1 (nth 1 NODE))
    (setq P2 (nth 2 NODE))
    (setq BULGE (last NODE))
    (if (listp BULGE)
     (progn
      (setq R (RFL:GETSPIRALR2 (nth 0 BULGE) (nth 1 BULGE) (nth 2 BULGE)))
      (if (> (sin (- (angle (nth 1 BULGE) (nth 2 BULGE)) (angle (nth 0 BULGE) (nth 1 BULGE)))) 0.0)
       (setq DIR 1.0)
       (setq DIR -1.0)
      )
      (if (< (distance (nth 1 NODE) (nth 2 BULGE))
             (distance (nth 2 NODE) (nth 2 BULGE)))
       (setq DIR (* DIR -1.0))
      )
     )
     (if (< (abs BULGE) TOL)
      (setq R 0.0 DIR 0.0)
      (progn
       (setq ATOTAL (* 4.0 (atan (abs BULGE))))
       (setq CHORD (distance P1 P2))
       (setq R (/ CHORD (* 2 (sin (/ ATOTAL 2)))))
       (setq DIR (SIGN BULGE))
      )
     )
    )
   )
  )
  (eval (* R DIR))
 )

 (defun GETLENGTH (NODE / ATOTAL BULGE CHORD L P1 P2 R)
  (if (= nil NODE)
   (setq L nil)
   (progn
    (setq P1 (nth 1 NODE))
    (setq P2 (nth 2 NODE))
    (setq BULGE (last NODE))
    (if (listp BULGE)
     (if (listp (last BULGE))
      (setq L (RFL:GETSPIRALLS2 (nth 0 BULGE) (nth 1 BULGE) (nth 2 BULGE)))
      (setq L (- (RFL:GETSPIRALLS2 (nth 0 BULGE) (nth 1 BULGE) (nth 2 BULGE)) (last BULGE)))
     )
     (if (< (abs BULGE) TOL)
      (setq L (distance P1 P2))
      (progn
       (setq ATOTAL (* 4.0 (atan (abs BULGE))))
       (setq CHORD (distance P1 P2))
       (setq R (/ CHORD (* 2 (sin (/ ATOTAL 2)))))
       (setq L (* R ATOTAL))
      )
     )
    )
   )
  )
  (eval L)
 )

 (defun LABELLINE (LABEL P STA / PS STA1 STA2 STAT TEXTHEIGHT)
  (if (= 0.0 (cdr (assoc 40 (tblsearch "STYLE" (getvar "TEXTSTYLE")))))
   (setq TEXTHEIGHT (cdr (assoc "TEXTH" RFL:SCHEMATLIST)))
   (setq TEXTHEIGHT nil)
  )
  (if (= 1 FR)
   (setq PS (list (- (+ (car PBASE) STA) STABASE) (cadr PBASE)))
   (setq PS (list (+ (- (car PBASE) STA) STABASE) (cadr PBASE)))
  )
  (setvar "ANGDIR" 0)(setvar "AUNITS" 1)(setvar "ANGBASE" 0)
;  (setvar "CLAYER" SLINELAYER)
  (command ".LINE" (list (nth 0 PS) (+ (nth 1 PS) (* 2 (cdr (assoc "ARCH" RFL:SCHEMATLIST)))))
                   (list (nth 0 PS) (+ (nth 1 PS) (* 11 (cdr (assoc "ARCH" RFL:SCHEMATLIST))))) "")
;  (setvar "CLAYER" STEXTLAYER)
  (setq STAT (strcat "STA: " (RFL:STATXT STA)))
  (if (= (cdr (assoc "NEON" RFL:SCHEMATLIST)) 0)
   (if (= TEXTHEIGHT nil)
    (progn
     (command ".TEXT" "BL" (list (nth 0 PS) (+ (nth 1 PS) (* 2 (cdr (assoc "ARCH" RFL:SCHEMATLIST)))))
              "90" LABEL)
     (command ".TEXT" "" STAT)
    )
    (progn
     (command ".TEXT" "BL" (list (nth 0 PS) (+ (nth 1 PS) (* 2 (cdr (assoc "ARCH" RFL:SCHEMATLIST)))))
              TEXTHEIGHT "90" LABEL)
     (command ".TEXT" "" STAT)
    )
   )
   (if (= TEXTHEIGHT nil)
    (progn
     (command ".TEXT" "BL" (list (nth 0 PS) (+ (nth 1 PS) (* 2 (cdr (assoc "ARCH" RFL:SCHEMATLIST)))))
              "90" (strcat LABEL ", " STAT))
     (command ".TEXT" "" (strcat "N:" (rtos (nth 1 P)) ", E:" (rtos (nth 0 P))))
    )
    (progn
     (command ".TEXT" "BL" (list (nth 0 PS) (+ (nth 1 PS) (* 2 (cdr (assoc "ARCH" RFL:SCHEMATLIST)))))
              TEXTHEIGHT "90" (strcat LABEL ", " STAT))
     (command ".TEXT" "" (strcat "N:" (rtos (nth 1 P)) ", E:" (rtos (nth 0 P))))
    )
   )
  )
 )

 (defun LABELAZ (P1 P2 STA / PS TEXTHEIGHT)
  (if (= 0.0 (cdr (assoc 40 (tblsearch "STYLE" (getvar "TEXTSTYLE")))))
   (setq TEXTHEIGHT (cdr (assoc "TEXTH" RFL:SCHEMATLIST)))
   (setq TEXTHEIGHT nil)
  )
  (if (= 1 FR)
   (setq PS (list (- (+ (car PBASE) STA (/ (distance P1 P2) 2.0)) STABASE) (cadr PBASE)))
   (setq PS (list (+ (- (car PBASE) STA (/ (distance P1 P2) 2.0)) STABASE) (cadr PBASE)))
  )
;  (setvar "CLAYER" STEXTLAYER)
  (setvar "ANGDIR" 0)(setvar "AUNITS" 1)(setvar "ANGBASE" 0)
  (if (= TEXTHEIGHT nil)
   (command ".TEXT" "BC" PS 0.0)
   (command ".TEXT" "BC" PS TEXTHEIGHT 0.0)
  )
  (setvar "ANGDIR" 1)(setvar "AUNITS" 1)(setvar "ANGBASE" (/ pi 2))
  (command (strcat "AZ " (vl-string-subst "%%d" "d" (angtos (angle P1 P2)))))
  (setvar "ANGDIR" 0)(setvar "AUNITS" 1)(setvar "ANGBASE" 0)
 )

 (defun LABELNODE (NODE / BULGE P1 P2 PS STA STR STR2 TEXTHEIGHT)
  (setvar "DIMZIN" 8)
  (if (listp (last NODE))
   (progn
    (setq BULGE (last NODE))
    (setq STR (strcat "Ls=" (rtos (RFL:GETSPIRALLS2 (nth 0 BULGE) (nth 1 BULGE) (nth 2 BULGE)))))
    (setq STR2 (strcat "A=" (rtos (RFL:GETSPIRALA2 (nth 0 BULGE) (nth 1 BULGE) (nth 2 BULGE)))))
   )
   (if (< (abs (last NODE)) TOL)
    (progn
     (setq STR nil STR2 nil)
    )
    (progn
     (setq STR (strcat "R=" (rtos (abs (GETRADIUS NODE)))))
     (setq STR2 nil)
    )
   )
  )
  (setvar "DIMZIN" 0)
  (if (/= STR nil)
   (progn
    (if (= 0.0 (cdr (assoc 40 (tblsearch "STYLE" (getvar "TEXTSTYLE")))))
     (setq TEXTHEIGHT (cdr (assoc "TEXTH" RFL:SCHEMATLIST)))
     (setq TEXTHEIGHT nil)
    )
    (setq STA (car NODE))
    (setq P1 (cadr NODE))
    (setq P2 (caddr NODE))
    (if (= 1 FR)
     (setq PS (list (- (+ (car PBASE) STA (/ (distance P1 P2) 2.0)) STABASE) (cadr PBASE)))
     (setq PS (list (+ (- (car PBASE) STA (/ (distance P1 P2) 2.0)) STABASE) (cadr PBASE)))
    )
;    (setvar "CLAYER" STEXTLAYER)
    (if (= TEXTHEIGHT nil)
     (progn
      (command ".TEXT" "TC" (list (nth 0 PS) (- (nth 1 PS) (* 2 (cdr (assoc "ARCH" RFL:SCHEMATLIST)))))
               "0" STR)
      (if (/= nil STR2) (command ".TEXT" "" STR2))
     )
     (progn
      (command ".TEXT" "TC" (list (nth 0 PS) (- (nth 1 PS) (* 2 (cdr (assoc "ARCH" RFL:SCHEMATLIST)))))
               TEXTHEIGHT "0" STR)
      (if (/= nil STR2) (command ".TEXT" "" STR2))
     )
    )
   )
  )
 )

 (if (= nil ALIGNLIST)
  (princ "\n*** NO ALIGNMENT DEFINED ***")
  (progn
   (while (= nil (setq PBASE (getpoint "\nBasepoint for schematic : "))))
   (setq STABASE (caar ALIGNLIST))
   (initget "Forward Reverse")
   (setq REP (getkword "\nForward (L to R) or Reverse (R to L) (Forward/Reverse) <Forward> : "))
   (if (= nil REP) (setq FR "Forward"))
   (if (= FR "Forward") (setq FR 1) (setq FR -1))
   (setq AL ALIGNLIST)
   (setq NODEPREV nil)
   (setq NODE (car AL))
   (setq NODENEXT (cadr AL))
   (cond ((= (CHECKCURVE NODE) 0) (LABELLINE "P.O.T." (cadr NODE) (car NODE)))
         ((= (CHECKCURVE NODE) 1) (LABELLINE "P.O.C." (cadr NODE) (car NODE)))
         ((= (CHECKCURVE NODE) 2) (LABELLINE "P.O.S." (cadr NODE) (car NODE)))
   )



   (while (/= NODE nil)
    (setq R (GETRADIUS NODE))
    (setq RNEXT (GETRADIUS NODENEXT))
    (if (and (= R 0.0) (= RNEXT 0.0) (/= NODENEXT nil))
     (progn
      (setq TIN (GETTANGENT "IN" NODE))
      (setq TOUT (GETTANGENT "OUT" NODENEXT))
      (if (= (cdr (assoc "AZON" RFL:SCHEMATLIST)) 1) (LABELAZ (cadr NODE) (caddr NODE) (car NODE)))
      (LABELLINE (cdr (assoc "TT" RFL:SCHEMATLIST)) (cadr NODENEXT) (car NODENEXT)) 
      (if (= 1 FR)
       (progn
        (setq P1 (list (- (+ (car PBASE) (car NODE)) STABASE) (cadr PBASE)))
        (setq P2 (list (- (+ (car PBASE) (car NODENEXT)) STABASE) (cadr PBASE)))
       )
       (progn
        (setq P1 (list (+ (- (car PBASE) (car NODE)) STABASE) (cadr PBASE)))
        (setq P2 (list (+ (- (car PBASE) (car NODENEXT)) STABASE) (cadr PBASE)))
       )
      )
      (command "._LINE" P1 P2 "")
      (setq NODEPREV NODE)
      (setq AL (cdr AL))
      (setq NODE (car AL))
      (setq NODENEXT (cadr AL))
     )
     (if (= R 0.0)
      (progn
       (if (= (cdr (assoc "AZON" RFL:SCHEMATLIST)) 1) (LABELAZ (cadr NODE) (caddr NODE) (car NODE)))
       (if (= 1 FR)
        (progn
         (setq P1 (list (- (+ (car PBASE) (car NODE)) STABASE) (cadr PBASE)))
         (setq P2 (list (- (+ (car PBASE) (car NODE) (GETLENGTH NODE)) STABASE) (cadr PBASE)))
        )
        (progn
         (setq P1 (list (+ (- (car PBASE) (car NODE)) STABASE) (cadr PBASE)))
         (setq P2 (list (+ (- (car PBASE) (car NODE) (GETLENGTH NODE)) STABASE) (cadr PBASE)))
        )
       )
       (command "._LINE" P1 P2 "")
       (setq NODEPREV NODE)
       (setq AL (cdr AL))
       (setq NODE (car AL))
       (setq NODENEXT (car (cdr AL)))
      )
      (progn
       (setq S1 nil S2 nil C1 nil)
       (setq N1 NODE)
       (setq TIN (GETTANGENT "IN" NODE))
       (if (and (= (CHECKCURVE NODE) 2)
                (< (abs (- (GETRADIUS NODE) R)) TOL)
           )
        (progn
         (setq S1 1)
         (cond ((= (CHECKCURVE NODEPREV) 0) (LABELLINE (cdr (assoc "TS" RFL:SCHEMATLIST)) (cadr NODE) (car NODE)))
               ((= (CHECKCURVE NODEPREV) 1) (LABELLINE (cdr (assoc "AS" RFL:SCHEMATLIST)) (cadr NODE) (car NODE)))
               ((= (CHECKCURVE NODEPREV) 2) (LABELLINE (cdr (assoc "SS" RFL:SCHEMATLIST)) (cadr NODE) (car NODE)))
         )
         (LABELNODE NODE) 
         (setq N2 NODE)
         (setq TOUT (GETTANGENT "OUT" NODE))
         (setq NODEPREV NODE)
         (setq AL (cdr AL))
         (setq NODE (car AL))
         (setq NODENEXT (car (cdr AL)))
        )
       )
       (if (and (= (CHECKCURVE NODE) 1)
                (< (abs (- (GETRADIUS NODE) R)) TOL)
           )
        (progn
         (setq C1 1)
         (cond ((= (CHECKCURVE NODEPREV) 0) (LABELLINE (cdr (assoc "TA" RFL:SCHEMATLIST)) (cadr NODE) (car NODE)))
               ((= (CHECKCURVE NODEPREV) 1) (LABELLINE (cdr (assoc "AA" RFL:SCHEMATLIST)) (cadr NODE) (car NODE)))
               ((= (CHECKCURVE NODEPREV) 2) (LABELLINE (cdr (assoc "SA" RFL:SCHEMATLIST)) (cadr NODE) (car NODE)))
         )
         (LABELNODE NODE)
         (setq N2 NODE)
         (setq TOUT (GETTANGENT "OUT" NODE))
         (setq NODEPREV NODE)
         (setq AL (cdr AL))
         (setq NODE (car AL))
         (setq NODENEXT (car (cdr AL)))
        )
       )
       (if (and (= (CHECKCURVE NODE) 2)
                (< (abs (- (GETRADIUS NODE) R)) TOL)
           )
        (progn
         (setq S2 1)
         (cond ((= (CHECKCURVE NODEPREV) 0) (LABELLINE (cdr (assoc "TS" RFL:SCHEMATLIST)) (cadr NODE) (car NODE)))
               ((= (CHECKCURVE NODEPREV) 1) (LABELLINE (cdr (assoc "AS" RFL:SCHEMATLIST)) (cadr NODE) (car NODE)))
               ((= (CHECKCURVE NODEPREV) 2) (LABELLINE (cdr (assoc "SS" RFL:SCHEMATLIST)) (cadr NODE) (car NODE)))
         )
         (LABELNODE NODE)
         (setq N2 NODE)
         (setq TOUT (GETTANGENT "OUT" NODE))
         (setq NODEPREV NODE)
         (setq AL (cdr AL))
         (setq NODE (car AL))
         (setq NODENEXT (car (cdr AL)))
        )
       )
       (if (/= NODE nil)
        (progn
         (cond ((= (CHECKCURVE NODEPREV) 0)
                (cond ((= (CHECKCURVE NODE) 0) (LABELLINE (cdr (assoc "TT" RFL:SCHEMATLIST)) (cadr NODE) (car NODE)))
                      ((= (CHECKCURVE NODE) 1) (LABELLINE (cdr (assoc "TA" RFL:SCHEMATLIST)) (cadr NODE) (car NODE)))
                      ((= (CHECKCURVE NODE) 2) (LABELLINE (cdr (assoc "TS" RFL:SCHEMATLIST)) (cadr NODE) (car NODE)))
                )
               )
               ((= (CHECKCURVE NODEPREV) 1)
                (cond ((= (CHECKCURVE NODE) 0) (LABELLINE (cdr (assoc "AT" RFL:SCHEMATLIST)) (cadr NODE) (car NODE)))
                      ((= (CHECKCURVE NODE) 1) (LABELLINE (cdr (assoc "AA" RFL:SCHEMATLIST)) (cadr NODE) (car NODE)))
                      ((= (CHECKCURVE NODE) 2) (LABELLINE (cdr (assoc "AS" RFL:SCHEMATLIST)) (cadr NODE) (car NODE)))
                )
               )
              ((= (CHECKCURVE NODEPREV) 2)
                (cond ((= (CHECKCURVE NODE) 0) (LABELLINE (cdr (assoc "ST" RFL:SCHEMATLIST)) (cadr NODE) (car NODE)))
                      ((= (CHECKCURVE NODE) 1) (LABELLINE (cdr (assoc "SA" RFL:SCHEMATLIST)) (cadr NODE) (car NODE)))
                      ((= (CHECKCURVE NODE) 2) (LABELLINE (cdr (assoc "SS" RFL:SCHEMATLIST)) (cadr NODE) (car NODE)))
                )
               )
         )
         (LABELNODE NODE)
        )
       )
       (if (/= R 0.0)
        (if (= 1 FR)
         (progn
          (setq PS (list (- (+ (car PBASE) (car N1)) STABASE) (cadr PBASE)))
          (setq P1 (list (- (+ (car PBASE) (car N1) (cdr (assoc "ARCH" RFL:SCHEMATLIST))) STABASE) (cadr PBASE)))
          (if (> R 0.0)
           (setq P2 (list (- (+ (car PBASE) (car N1) (cdr (assoc "ARCH" RFL:SCHEMATLIST))) STABASE) (- (cadr PBASE) (cdr (assoc "ARCH" RFL:SCHEMATLIST)))))
           (setq P2 (list (- (+ (car PBASE) (car N1) (cdr (assoc "ARCH" RFL:SCHEMATLIST))) STABASE) (+ (cadr PBASE) (cdr (assoc "ARCH" RFL:SCHEMATLIST)))))
          )
          (if (> R 0.0)
           (command "._ARC" PS "C" P1 P2)
           (command "._ARC" P2 "C" P1 PS)
          )
          (setq PS (list (- (+ (car PBASE) (car N2) (GETLENGTH N2)) STABASE) (cadr PBASE)))
          (setq P1 (list (- (+ (car PBASE) (car N2) (GETLENGTH N2)) STABASE (cdr (assoc "ARCH" RFL:SCHEMATLIST))) (cadr PBASE)))
          (if (> R 0.0)
           (setq P2 (list (- (+ (car PBASE) (car N2) (GETLENGTH N2)) STABASE (cdr (assoc "ARCH" RFL:SCHEMATLIST))) (- (cadr PBASE) (cdr (assoc "ARCH" RFL:SCHEMATLIST)))))
           (setq P2 (list (- (+ (car PBASE) (car N2) (GETLENGTH N2)) STABASE (cdr (assoc "ARCH" RFL:SCHEMATLIST))) (+ (cadr PBASE) (cdr (assoc "ARCH" RFL:SCHEMATLIST)))))
          )
          (if (> R 0.0)
           (command "._ARC" P2 "C" P1 PS)
           (command "._ARC" PS "C" P1 P2)
          )
          (if (> R 0.0)
           (setq P1 (list (- (+ (car PBASE) (car N1) (cdr (assoc "ARCH" RFL:SCHEMATLIST))) STABASE) (- (cadr PBASE) (cdr (assoc "ARCH" RFL:SCHEMATLIST)))))
           (setq P1 (list (- (+ (car PBASE) (car N1) (cdr (assoc "ARCH" RFL:SCHEMATLIST))) STABASE) (+ (cadr PBASE) (cdr (assoc "ARCH" RFL:SCHEMATLIST)))))
          )
          (if (> R 0.0)
           (setq P2 (list (- (+ (car PBASE) (car N2) (GETLENGTH N2)) STABASE (cdr (assoc "ARCH" RFL:SCHEMATLIST))) (- (cadr PBASE) (cdr (assoc "ARCH" RFL:SCHEMATLIST)))))
           (setq P2 (list (- (+ (car PBASE) (car N2) (GETLENGTH N2)) STABASE (cdr (assoc "ARCH" RFL:SCHEMATLIST))) (+ (cadr PBASE) (cdr (assoc "ARCH" RFL:SCHEMATLIST)))))
          )
          (command "._LINE" P1 P2 "")
         )
         (progn
          (setq PS (list (+ (- (car PBASE) (car N1)) STABASE) (cadr PBASE)))
          (setq P1 (list (+ (- (car PBASE) (car N1) (cdr (assoc "ARCH" RFL:SCHEMATLIST))) STABASE) (cadr PBASE)))
          (if (> R 0.0)
           (setq P2 (list (+ (- (car PBASE) (car N1) (cdr (assoc "ARCH" RFL:SCHEMATLIST))) STABASE) (+ (cadr PBASE) (cdr (assoc "ARCH" RFL:SCHEMATLIST)))))
           (setq P2 (list (+ (- (car PBASE) (car N1) (cdr (assoc "ARCH" RFL:SCHEMATLIST))) STABASE) (- (cadr PBASE) (cdr (assoc "ARCH" RFL:SCHEMATLIST)))))
          )
          (if (> R 0.0)
           (command "._ARC" PS "C" P1 P2)
           (command "._ARC" P2 "C" P1 PS)
          )
          (setq PS (list (+ (- (car PBASE) (car N2) (GETLENGTH N2)) STABASE) (cadr PBASE)))
          (setq P1 (list (+ (- (car PBASE) (car N2) (GETLENGTH N2)) STABASE (cdr (assoc "ARCH" RFL:SCHEMATLIST))) (cadr PBASE)))
          (if (> R 0.0)
           (setq P2 (list (+ (- (car PBASE) (car N2) (GETLENGTH N2)) STABASE (cdr (assoc "ARCH" RFL:SCHEMATLIST))) (+ (cadr PBASE) (cdr (assoc "ARCH" RFL:SCHEMATLIST)))))
           (setq P2 (list (+ (- (car PBASE) (car N2) (GETLENGTH N2)) STABASE (cdr (assoc "ARCH" RFL:SCHEMATLIST))) (- (cadr PBASE) (cdr (assoc "ARCH" RFL:SCHEMATLIST)))))
          )
          (if (> R 0.0)
           (command "._ARC" P2 "C" P1 PS)
           (command "._ARC" PS "C" P1 P2)
          )
          (if (> R 0.0)
           (setq P1 (list (+ (- (car PBASE) (car N1) (cdr (assoc "ARCH" RFL:SCHEMATLIST))) STABASE) (+ (cadr PBASE) (cdr (assoc "ARCH" RFL:SCHEMATLIST)))))
           (setq P1 (list (+ (- (car PBASE) (car N1) (cdr (assoc "ARCH" RFL:SCHEMATLIST))) STABASE) (- (cadr PBASE) (cdr (assoc "ARCH" RFL:SCHEMATLIST)))))
          )
          (if (> R 0.0)
           (setq P2 (list (+ (- (car PBASE) (car N2) (GETLENGTH N2)) STABASE (cdr (assoc "ARCH" RFL:SCHEMATLIST))) (+ (cadr PBASE) (cdr (assoc "ARCH" RFL:SCHEMATLIST)))))
           (setq P2 (list (+ (- (car PBASE) (car N2) (GETLENGTH N2)) STABASE (cdr (assoc "ARCH" RFL:SCHEMATLIST))) (- (cadr PBASE) (cdr (assoc "ARCH" RFL:SCHEMATLIST)))))
          )
          (command "._LINE" P1 P2 "")
         )
        )
       )
      )
     )
    )         
   )

   (if (= NODE nil) (setq NODE NODEPREV))
   (cond ((= (CHECKCURVE NODE) 0) (LABELLINE "P.O.T." (caddr NODE) (+ (car NODE) (GETLENGTH NODE))))
         ((= (CHECKCURVE NODE) 1) (LABELLINE "P.O.C." (caddr NODE) (+ (car NODE) (GETLENGTH NODE))))
         ((= (CHECKCURVE NODE) 2) (LABELLINE "P.O.S." (caddr NODE) (+ (car NODE) (GETLENGTH NODE))))
   )



  )
 )

 (command "._UCS" "P")
 (setvar "CMDECHO" CMDECHO)
 (setvar "CLAYER" CLAYER)
 (setvar "DIMZIN" DIMZIN)
 (setvar "OSMODE" OSMODE)
 (setvar "ATTREQ" ATTREQ)
 (setvar "ANGBASE" ANGBASE)
 (setvar "ANGDIR" ANGDIR)
)
