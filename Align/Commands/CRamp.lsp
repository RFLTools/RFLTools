;
;
;     Program written by Robert Livingston, 03-06-11
;     Modified 2014-11-07 to store ramp details into nose and add functionality
;
;     C:RAMP is a utility for drawing exit and entrance ramp tapers
;
;     C:RAMPTAPERLABEL : Toggles labelling of taper
;     C:MOVENOSE       : Moves the nose to a new location
;     C:UPDATENODE     : Updates the nose to it's current location
;     C:SETNOSE        : Sets nos to it's current location
;     C:ERASENOSE      : Erases the nose
;     RFL:RAMPPUTXDATA : Adds extended data to entity
;     RFL:RAMPGETXDATA : Reads extended data from entity
;
(setq RFL:RAMPTAPERLABEL T)
(defun C:RAMPTAPERLABEL ()
 (if RFL:RAMPTAPERLABEL (setq RFL:RAMPTAPERLABEL nil) (setq RFL:RAMPTAPERLABEL T))
)
(setq RFL:RAMPLIST (list (cons "LANEOFFSET" 0.0)
                         (cons "RAMPTAPER" 20.0)
                         (cons "RAMPTAPERENTRANCE" 40.0)
                         (cons "RAMPTAPEREXIT" 20.0)
                         (cons "RAMPVERTICIES" 50)
                         (cons "WEAVEOFFSET" 8.5)
                         (cons "WEAVEOFFSETENTRANCESINGLE" 5.3)
                         (cons "WEAVEOFFSETENTRANCEDUAL" 7.9)
                         (cons "WEAVEOFFSETEXITSINGLE" 8.5)
                         (cons "WEAVEOFFSETEXITDUAL" 11.1)
                         (cons "GOREWIDTH" 5.5)
                         (cons "GOREWIDTHENTRANCESINGLE" 5.3)
                         (cons "GOREWIDTHENTRANCEDUAL" 7.9)
                         (cons "GOREWIDTHEXITSINGLE" 5.5)
                         (cons "GOREWIDTHEXITDUAL" 8.1)
                         (cons "TAPEROFFSET" 0.5)
                         (cons "TAPEROFFSETENTRANCE" 0.0)
                         (cons "TAPEROFFSETEXIT" 0.5)
                         (cons "INSIDEVERTICIES" 25)
                         (cons "NOSESTATION" 0.0)
                         (cons "NOSEOFFSET" 3.0)
                         (cons "NOSERADIUS" 1.1)
                         (cons "NOSERADIUSENTRANCE" 0.6)
                         (cons "NOSERADIUSEXIT" 1.1)
                         (cons "INSIDESHOULDER" 1.0)
                         (cons "INSIDESHOULDERSINGLE" 1.0)
                         (cons "INSIDESHOULDERDUAL" 2.0)
                         (cons "LANEWIDTH" 4.8)
                         (cons "LANEWIDTHSINGLE" 4.8)
                         (cons "LANEWIDTHDUAL" 7.4)
                         (cons "RETURNTAPER" 20.0)
                         (cons "RETURNOFFSET" 3.0)
                         (cons "RETURNVERTICIES" 10)
                         (cons "SINGLELANE" "1")
                         (cons "DUALLANE" "0")
                         (cons "UPCHAINAGE" "1")
                         (cons "DOWNCHAINAGE" "0")
                         (cons "RIGHTSIDE" "1")
                         (cons "LEFTSIDE" "0")
                         (cons "EXITTERMINAL" "1")
                         (cons "ENTRANCETERMINAL" "0")))
(defun C:RAMP (/ *error* ACCEPTRAMP ALSAVE ANGBASE ANGDIR C CANCEL CANCELRAMP CLAYER
                 CMDECHO D1 D2 DCL_ID DIMZIN ENTNOSE ENTNOSELIST FIXNUMBER
                 INITIATE ORTHOMODE OSMODE RERUN SETDUALLANE SETENTRANCE SETEXIT
                 SETSINGLELANE TEMPRAMPLIST)

 (command "._UNDO" "M")

 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq CLAYER (getvar "CLAYER"))
 (setq DIMZIN (getvar "DIMZIN"))
 (setvar "DIMZIN" 0)
 (setq OSMODE (getvar "OSMODE"))
 (setvar "OSMODE" 0)
 (setq ORTHOMODE (getvar "ORTHOMODE"))
 (setvar "ORTHOMODE" 0)
 (setq PLINETYPE (getvar "PLINETYPE"))
 (setvar "PLINETYPE" 2)
 (setq ALSAVE RFL:ALIGNLIST)

 (defun *error* (msg)
  (setvar "CMDECHO" CMDECHO)
  (setvar "ANGBASE" ANGBASE)
  (setvar "ANGDIR" ANGDIR)
  (setvar "CLAYER" CLAYER)
  (setvar "DIMZIN" DIMZIN)
  (setvar "OSMODE" OSMODE)
  (setvar "ORTHOMODE" ORTHOMODE)
  (setvar "PLINETYPE" PLINETYPE)
  (setq RFL:ALIGNLIST ALSAVE)
  ;(setq *error* nil)
  (print msg)
 )

 (defun INITIATE (RFL:RAMPLIST)
  (start_image "IMAGE1")
  (slide_image 0 0 (- (dimx_tile "IMAGE1") 1) (- (dimy_tile "IMAGE1") 1) (strcat RFLALIGNSLBNAME "(Tapered Single Exit)"))
  (end_image)
  (set_tile "LANEOFFSET" (rtos (cdr (assoc "LANEOFFSET" RFL:RAMPLIST))))
  (set_tile "RAMPTAPER" (rtos (cdr (assoc "RAMPTAPER" RFL:RAMPLIST))))
  (set_tile "RAMPVERTICIES" (itoa (cdr (assoc "RAMPVERTICIES" RFL:RAMPLIST))))
  (set_tile "WEAVEOFFSET" (rtos (cdr (assoc "WEAVEOFFSET" RFL:RAMPLIST))))
  (set_tile "GOREWIDTH" (rtos (cdr (assoc "GOREWIDTH" RFL:RAMPLIST))))
  (set_tile "TAPEROFFSET" (rtos (cdr (assoc "TAPEROFFSET" RFL:RAMPLIST))))
  (set_tile "INSIDEVERTICIES" (itoa (cdr (assoc "INSIDEVERTICIES" RFL:RAMPLIST))))
  (set_tile "NOSESTATION" (rtos (cdr (assoc "NOSESTATION" RFL:RAMPLIST))))
  (set_tile "NOSEOFFSET" (rtos (cdr (assoc "NOSEOFFSET" RFL:RAMPLIST))))
  (set_tile "NOSERADIUS" (rtos (cdr (assoc "NOSERADIUS" RFL:RAMPLIST))))
  (set_tile "INSIDESHOULDER" (rtos (cdr (assoc "INSIDESHOULDER" RFL:RAMPLIST))))
  (set_tile "LANEWIDTH" (rtos (cdr (assoc "LANEWIDTH" RFL:RAMPLIST))))
  (set_tile "RETURNTAPER" (rtos (cdr (assoc "RETURNTAPER" RFL:RAMPLIST))))
  (set_tile "RETURNOFFSET" (rtos (cdr (assoc "RETURNOFFSET" RFL:RAMPLIST))))
  (set_tile "RETURNVERTICIES" (itoa (cdr (assoc "RETURNVERTICIES" RFL:RAMPLIST))))
  (set_tile "SINGLELANE" (cdr (assoc "SINGLELANE" RFL:RAMPLIST)))
  (set_tile "DUALLANE" (cdr (assoc "DUALLANE" RFL:RAMPLIST)))
  (set_tile "UPCHAINAGE" (cdr (assoc "UPCHAINAGE" RFL:RAMPLIST)))
  (set_tile "DOWNCHAINAGE" (cdr (assoc "DOWNCHAINAGE" RFL:RAMPLIST)))
  (set_tile "RIGHTSIDE" (cdr (assoc "RIGHTSIDE" RFL:RAMPLIST)))
  (set_tile "LEFTSIDE" (cdr (assoc "LEFTSIDE" RFL:RAMPLIST)))
  (set_tile "EXITTERMINAL" (cdr (assoc "EXITTERMINAL" RFL:RAMPLIST)))
  (set_tile "ENTRANCETERMINAL" (cdr (assoc "ENTRANCETERMINAL" RFL:RAMPLIST)))
 )

 (defun CANCELRAMP ()
  (setq CANCEL 1)
  (done_dialog)
  (unload_dialog DCL_ID)
 )

 (defun ACCEPTRAMP ()
  (setq CANCEL 0)
  (setq RFL:RAMPLIST (list (cons "LANEOFFSET" (atof (get_tile "LANEOFFSET")))
                           (cons "RAMPTAPER" (atof (get_tile "RAMPTAPER")))
                           (cons "RAMPTAPERENTRANCE" (cdr (assoc "RAMPTAPERENTRANCE" RFL:RAMPLIST)))
                           (cons "RAMPTAPEREXIT" (cdr (assoc "RAMPTAPEREXIT" RFL:RAMPLIST)))
                           (cons "RAMPVERTICIES" (atoi (get_tile "RAMPVERTICIES")))
                           (cons "WEAVEOFFSET" (atof (get_tile "WEAVEOFFSET")))
                           (cons "WEAVEOFFSETENTRANCESINGLE" (cdr (assoc "WEAVEOFFSETENTRANCESINGLE" RFL:RAMPLIST)))
                           (cons "WEAVEOFFSETENTRANCEDUAL" (cdr (assoc "WEAVEOFFSETENTRANCEDUAL" RFL:RAMPLIST)))
                           (cons "WEAVEOFFSETEXITSINGLE" (cdr (assoc "WEAVEOFFSETEXITSINGLE" RFL:RAMPLIST)))
                           (cons "WEAVEOFFSETEXITDUAL" (cdr (assoc "WEAVEOFFSETEXITDUAL" RFL:RAMPLIST)))
                           (cons "GOREWIDTH" (atof (get_tile "GOREWIDTH")))
                           (cons "GOREWIDTHENTRANCESINGLE" (cdr (assoc "GOREWIDTHENTRANCESINGLE" RFL:RAMPLIST)))
                           (cons "GOREWIDTHENTRANCEDUAL" (cdr (assoc "GOREWIDTHENTRANCEDUAL" RFL:RAMPLIST)))
                           (cons "GOREWIDTHEXITSINGLE" (cdr (assoc "GOREWIDTHEXITSINGLE" RFL:RAMPLIST)))
                           (cons "GOREWIDTHEXITDUAL" (cdr (assoc "GOREWIDTHEXITDUAL" RFL:RAMPLIST)))
                           (cons "TAPEROFFSET" (atof (get_tile "TAPEROFFSET")))
                           (cons "TAPEROFFSETENTRANCE" (cdr (assoc "TAPEROFFSETENTRANCE" RFL:RAMPLIST)))
                           (cons "TAPEROFFSETEXIT" (cdr (assoc "TAPEROFFSETEXIT" RFL:RAMPLIST)))
                           (cons "INSIDEVERTICIES" (atoi (get_tile "INSIDEVERTICIES")))
                           (cons "NOSESTATION" (atof (get_tile "NOSESTATION")))
                           (cons "NOSEOFFSET" (atof (get_tile "NOSEOFFSET")))
                           (cons "NOSERADIUS" (atof (get_tile "NOSERADIUS")))
                           (cons "NOSERADIUSENTRANCE" (cdr (assoc "NOSERADIUSENTRANCE" RFL:RAMPLIST)))
                           (cons "NOSERADIUSEXIT" (cdr (assoc "NOSERADIUSEXIT" RFL:RAMPLIST)))
                           (cons "INSIDESHOULDER" (atof (get_tile "INSIDESHOULDER")))
                           (cons "INSIDESHOULDERSINGLE" (cdr (assoc "INSIDESHOULDERSINGLE" RFL:RAMPLIST)))
                           (cons "INSIDESHOULDERDUAL" (cdr (assoc "INSIDESHOULDERDUAL" RFL:RAMPLIST)))
                           (cons "LANEWIDTH" (atof (get_tile "LANEWIDTH")))
                           (cons "LANEWIDTHSINGLE" (cdr (assoc "LANEWIDTHSINGLE" RFL:RAMPLIST)))
                           (cons "LANEWIDTHDUAL" (cdr (assoc "LANEWIDTHDUAL" RFL:RAMPLIST)))
                           (cons "RETURNTAPER" (atof (get_tile "RETURNTAPER")))
                           (cons "RETURNOFFSET" (atof (get_tile "RETURNOFFSET")))
                           (cons "RETURNVERTICIES" (atoi (get_tile "RETURNVERTICIES")))
                           (cons "SINGLELANE" (get_tile "SINGLELANE"))
                           (cons "DUALLANE" (get_tile "DUALLANE"))
                           (cons "UPCHAINAGE" (get_tile "UPCHAINAGE"))
                           (cons "DOWNCHAINAGE" (get_tile "DOWNCHAINAGE"))
                           (cons "RIGHTSIDE" (get_tile "RIGHTSIDE"))
                           (cons "LEFTSIDE" (get_tile "LEFTSIDE"))
                           (cons "EXITTERMINAL" (get_tile "EXITTERMINAL"))
                           (cons "ENTRANCETERMINAL" (get_tile "ENTRANCETERMINAL"))))
  (done_dialog)
  (unload_dialog DCL_ID)
 )

 (defun FIXNUMBER (TYPE TILE)
  (if (= TYPE 1)
   (set_tile TILE (rtos (atof (get_tile TILE))))
   (set_tile TILE (itoa (atoi (get_tile TILE))))
  )
 )

 (defun SETSINGLELANE ()
  (set_tile "LANEWIDTH" (rtos (cdr (assoc "LANEWIDTHSINGLE" RFL:RAMPLIST))))
  (set_tile "INSIDESHOULDER" (rtos (cdr (assoc "INSIDESHOULDERSINGLE" RFL:RAMPLIST))))
  (if (= "1" (get_tile "EXITTERMINAL"))
   (SETEXIT)
   (SETENTRANCE)
  )
 )

 (defun SETDUALLANE ()
  (set_tile "LANEWIDTH" (rtos (cdr (assoc "LANEWIDTHDUAL" RFL:RAMPLIST))))
  (set_tile "INSIDESHOULDER" (rtos (cdr (assoc "INSIDESHOULDERDUAL" RFL:RAMPLIST))))
  (if (= "1" (get_tile "EXITTERMINAL"))
   (SETEXIT)
   (SETENTRANCE)
  )
 )

 (defun SETEXIT ()
  (set_tile "RAMPTAPER" (rtos (cdr (assoc "RAMPTAPEREXIT" RFL:RAMPLIST))))
  (set_tile "NOSERADIUS" (rtos (cdr (assoc "NOSERADIUSEXIT" RFL:RAMPLIST))))
  (set_tile "TAPEROFFSET" (rtos (cdr (assoc "TAPEROFFSETEXIT" RFL:RAMPLIST))))
  (if (= "1" (get_tile "SINGLELANE"))
   (progn
    (set_tile "GOREWIDTH" (rtos (cdr (assoc "GOREWIDTHEXITSINGLE" RFL:RAMPLIST))))
    (set_tile "WEAVEOFFSET" (rtos (cdr (assoc "WEAVEOFFSETEXITSINGLE" RFL:RAMPLIST))))
   )
   (progn
    (set_tile "GOREWIDTH" (rtos (cdr (assoc "GOREWIDTHEXITDUAL" RFL:RAMPLIST))))
    (set_tile "WEAVEOFFSET" (rtos (cdr (assoc "WEAVEOFFSETEXITDUAL" RFL:RAMPLIST))))
   )
  )
 )

 (defun SETENTRANCE ()
  (set_tile "RAMPTAPER" (rtos (cdr (assoc "RAMPTAPERENTRANCE" RFL:RAMPLIST))))
  (set_tile "NOSERADIUS" (rtos (cdr (assoc "NOSERADIUSENTRANCE" RFL:RAMPLIST))))
  (set_tile "TAPEROFFSET" (rtos (cdr (assoc "TAPEROFFSETENTRANCE" RFL:RAMPLIST))))
  (if (= "1" (get_tile "SINGLELANE"))
   (progn
    (set_tile "GOREWIDTH" (rtos (cdr (assoc "GOREWIDTHENTRANCESINGLE" RFL:RAMPLIST))))
    (set_tile "WEAVEOFFSET" (rtos (cdr (assoc "WEAVEOFFSETENTRANCESINGLE" RFL:RAMPLIST))))
   )
   (progn
    (set_tile "GOREWIDTH" (rtos (cdr (assoc "GOREWIDTHENTRANCEDUAL" RFL:RAMPLIST))))
    (set_tile "WEAVEOFFSET" (rtos (cdr (assoc "WEAVEOFFSETENTRANCEDUAL" RFL:RAMPLIST))))
   )
  )
 )

 (defun PICK ()
  (setq RERUN 1)
  (setq TEMPRAMPLIST RFL:RAMPLIST)
  (ACCEPTRAMP)
  (setq CANCEL "PICK")
 )

 (if (or (= nil RFL:ALIGNLIST) (= nil RFL:STAOFF))
  (alert "\n!!!!!  Alignment and/or alignment utilities not loaded !!!!!")
  (progn
   (setq RERUN 1)
   (setq PICKSTA nil)
   (setq TEMPRAMPLIST RFL:RAMPLIST)
   (while (= RERUN 1)
    (setq RERUN 0)


    (if (= RAMPDCLNAME nil)
     (progn
      (setq RAMPDCLNAME (vl-filename-mktemp "rfl.dcl"))
      (RFL:MAKEDCL RAMPDCLNAME "RAMP")
     )
     (if (= nil (findfile RAMPDCLNAME))
      (progn
       (setq RAMPDCLNAME (vl-filename-mktemp "rfl.dcl"))
       (RFL:MAKEDCL RAMPDCLNAME "RAMP")
      )
     )
    )
    (setq RFLALIGNSLBNAME "rflAlign.slb")
    (if (= nil (findfile RFLALIGNSLBNAME))
     (progn
      (setq RFLALIGNSLBNAME (vl-filename-mktemp "rfl.slb"))
      (RFL:MAKERFLSLB RFLALIGNSLBNAME)
     )
    )
    (setq DCL_ID (load_dialog RAMPDCLNAME))
    (if (not (new_dialog "RAMP" DCL_ID)) (exit))

    (INITIATE RFL:RAMPLIST)

    (if (/= nil PICKSTA)
     (progn
      (set_tile "NOSESTATION" (rtos PICKSTA))
      (setq RFL:RAMPLIST TEMPRAMPLIST)
      (setq PICKSTA nil)
     )
    )

    (action_tile "LANEOFFSET" "(FIXNUMBER 1 \"LANEOFFSET\")")
    (action_tile "RAMPTAPER" "(FIXNUMBER 1 \"RAMPTAPER\")")
    (action_tile "RAMPVERTICIES" "(FIXNUMBER 2 \"RAMPVERTICIES\")")
    (action_tile "WEAVEOFFSET" "(FIXNUMBER 1 \"WEAVEOFFSET\")")
    (action_tile "GOREWIDTH" "(FIXNUMBER 1 \"GOREWIDTH\")")
    (action_tile "TAPEROFFSET" "(FIXNUMBER 1 \"TAPEROFFSET\")")
    (action_tile "INSIDEVERTICIES" "(FIXNUMBER 2 \"INSIDEVERTICIES\")")
    (action_tile "NOSESTATION" "(FIXNUMBER 1 \"NOSESTATION\")")
    (action_tile "NOSERADIUS" "(FIXNUMBER 1 \"NOSERADIUS\")")
    (action_tile "INSIDESHOULDER" "(FIXNUMBER 1 \"INSIDESHOULDER\")")
    (action_tile "LANEWIDTH" "(FIXNUMBER 1 \"LANEWIDTH\")")
    (action_tile "RETURNTAPER" "(FIXNUMBER 1 \"RETURNTAPER\")")
    (action_tile "RETURNOFFSET" "(FIXNUMBER 1 \"RETURNOFFSET\")")
    (action_tile "RETURNVERTICIES" "(FIXNUMBER 2 \"RETURNVERTICIES\")")
    (action_tile "SINGLELANE" "(SETSINGLELANE)")
    (action_tile "DUALLANE" "(SETDUALLANE)")
    (action_tile "EXITTERMINAL" "(SETEXIT)")
    (action_tile "ENTRANCETERMINAL" "(SETENTRANCE)")
    (action_tile "PICK" "(PICK)")
    (action_tile "OK" "(ACCEPTRAMP)")
    (action_tile "CANCEL" "(CANCELRAMP)")

    (start_dialog)

    (if (= CANCEL "PICK")
     (setq PICKSTA (car (RFL:STAOFF (getpoint "\nPick point :"))))
    )
   )

   (if (= CANCEL 0)
    (progn
     (vl-load-com)
     (regapp "RFLTOOLS_XENT")
     (if (= "1" (cdr (assoc "UPCHAINAGE" RFL:RAMPLIST)))
      (setq D1 1.0)
      (setq D1 -1.0)
     )
     (if (= "1" (cdr (assoc "EXITTERMINAL" RFL:RAMPLIST)))
      (setq D2 1.0)
      (setq D2 -1.0)
     )
     (if (= "1" (cdr (assoc "LEFTSIDE" RFL:RAMPLIST)))
      (setq D1 (* D1 -1.0) D2 (* D2 -1.0))
     )
     (entmake)
     (entmake (list (cons 0 "CIRCLE")
                    (append (list 10) (RFL:XY (list (cdr (assoc "NOSESTATION" RFL:RAMPLIST))
                                                    (* D1
                                                       (+ (cdr (assoc "LANEOFFSET" RFL:RAMPLIST))
                                                          (cdr (assoc "NOSEOFFSET" RFL:RAMPLIST))
                                                          (cdr (assoc "NOSERADIUS" RFL:RAMPLIST))
                                                       )
                                                    )
                                              )
                                      )
                    )
                    (cons 40 (cdr (assoc "NOSERADIUS" RFL:RAMPLIST)))
              )
     )
;     (command "._CIRCLE"
;              (RFL:XY (list (cdr (assoc "NOSESTATION" RFL:RAMPLIST))
;                            (* D1
;                               (+ (cdr (assoc "LANEOFFSET" RFL:RAMPLIST))
;                                  (cdr (assoc "NOSEOFFSET" RFL:RAMPLIST))
;                                  (cdr (assoc "NOSERADIUS" RFL:RAMPLIST))
;                               )
;                            )
;                      )
;              )
;              (cdr (assoc "NOSERADIUS" RFL:RAMPLIST))
;     )
     (setq ENTNOSE (entlast))
     (RFL:RAMPPUTXDATA ENTNOSE nil)
     (RFL:RAMPDRAW ENTNOSE 0)
    )
   )
  )
 )


 (setvar "CMDECHO" CMDECHO)
 (setvar "ANGBASE" ANGBASE)
 (setvar "ANGDIR" ANGDIR)
 (setvar "CLAYER" CLAYER)
 (setvar "DIMZIN" DIMZIN)
 (setvar "OSMODE" OSMODE)
 (setvar "ORTHOMODE" ORTHOMODE)
 (setvar "PLINETYPE" PLINETYPE)
 (setq RFL:ALIGNLIST ALSAVE)
 nil
)
(defun RFL:RAMPDRAW (ENTNOSE MODE / ALSAVE ANG ANG2 ANGBASE ANGDIR C CMDECHO D1 D2 DIMZIN DOFFSET DSTA ENTDELSET ENTLISTNEW ENTNOSELIST
                                    ENTNOSEP ENTSET NOSEALIGNRADIUS NOSEOFFSET NOSERADIUS NOSESTATION OFFSET OFFSET1 OFFSET2
                                    ORTHOMODE OSMODE RLSAVE P P1 P2 PL1 PL2
                                    PICK PICKSTA PLINETYPE RAMPENTLIST RLSAVE STA STA1 STA2)
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq CLAYER (getvar "CLAYER"))
 (setq DIMZIN (getvar "DIMZIN"))
 (setvar "DIMZIN" 0)
 (setq OSMODE (getvar "OSMODE"))
 (setvar "OSMODE" 0)
 (setq ORTHOMODE (getvar "ORTHOMODE"))
 (setvar "ORTHOMODE" 0)
 (setq PLINETYPE (getvar "PLINETYPE"))
 (setvar "PLINETYPE" 2)
 (setq ALSAVE RFL:ALIGNLIST)
 (setq RLSAVE RFL:RAMPLIST)

 (defun *error* (msg)
  (setvar "CMDECHO" CMDECHO)
  (setvar "ANGBASE" ANGBASE)
  (setvar "ANGDIR" ANGDIR)
  (setvar "CLAYER" CLAYER)
  (setvar "DIMZIN" DIMZIN)
  (setvar "OSMODE" OSMODE)
  (setvar "ORTHOMODE" ORTHOMODE)
  (setvar "PLINETYPE" PLINETYPE)
  (setq RFL:ALIGNLIST ALSAVE)
  (setq RFL:RAMPLIST RLSAVE)
  ;(setq *error* nil)
  (print msg)
 )
 
 (defun GETBIT (N B)
  (while (> B 0)
   (setq N (/ N 2))
   (setq B (- B 1))
  )
  (rem N 2)
 )

 (setq ALSAVE RFL:ALIGNLIST)
 (setq RFL:ALIGNLIST (RFL:RAMPGETALIGN ENTNOSE))
 (setq ENTNOSELIST (entget ENTNOSE))
 (setq NOSESTATION (RFL:STAOFF (cdr (assoc 10 ENTNOSELIST))))
 (setq NOSERADIUS (cdr (assoc 40 ENTNOSELIST)))
 (if (= nil NOSESTATION)
  (princ "!!! NOSE NOT ON ALIGNMENT !!!")
  (progn
   (setq NOSEOFFSET (cadr NOSESTATION))
   (setq NOSESTATION (car NOSESTATION))
   (setq NOSEALIGNRADIUS (RFL:GETRADIUS NOSESTATION))
   (setq RLSAVE RFL:RAMPLIST)
   (setq RFL:RAMPLIST (RFL:RAMPGETRAMP ENTNOSE))
   (if (= nil RFL:RAMPLIST)
    (princ "\n*** NO NOSE DATA FOUND ***")
    (progn
     (setq ENTSET (ssadd))
     (if (= 1 (GETBIT MODE 0))
      (progn
       (setq RFL:RAMPLIST (subst (cons "NOSESTATION" NOSESTATION) (assoc "NOSESTATION" RFL:RAMPLIST) RFL:RAMPLIST))
      )
     )
     (if (= 1 (GETBIT MODE 1))
      (progn
      )
     )
     (if (= 1 (GETBIT MODE 2))
      (progn
       (setq ENTDELSET (RFL:RAMPGETENT ENTNOSE))
       (setq C 0)
       (while (< C (sslength ENTDELSET))
        (entdel (ssname ENTDELSET C))
        (setq C (+ C 1))
       )
;       (command "._ERASE" (RFL:RAMPGETENT ENTNOSE) "")
      )
     )
     (if (= "1" (cdr (assoc "UPCHAINAGE" RFL:RAMPLIST)))
      (setq D1 1.0)
      (setq D1 -1.0)
     )
     (if (= "1" (cdr (assoc "EXITTERMINAL" RFL:RAMPLIST)))
      (setq D2 1.0)
      (setq D2 -1.0)
     )
     (if (= "1" (cdr (assoc "LEFTSIDE" RFL:RAMPLIST)))
      (setq D1 (* D1 -1.0) D2 (* D2 -1.0))
     )

     (setq ENTNOSEP (RFL:XY (list (cdr (assoc "NOSESTATION" RFL:RAMPLIST))
                                  (* D1
                                     (+ (cdr (assoc "LANEOFFSET" RFL:RAMPLIST))
                                        (cdr (assoc "NOSEOFFSET" RFL:RAMPLIST))
                                        (cdr (assoc "NOSERADIUS" RFL:RAMPLIST))
                                     )
                                  )
                            )
                    )
     )
     (entmod (subst (list 10 (car ENTNOSEP) (cadr ENTNOSEP) 0.0) (assoc 10 (entget ENTNOSE)) (entget ENTNOSE)))

     (setq ANG (atan (/ 1.0 (cdr (assoc "RAMPTAPER" RFL:RAMPLIST)))))
     (setq STA2 (+ (cdr (assoc "NOSESTATION" RFL:RAMPLIST))
                   (* (+ (cdr (assoc "NOSERADIUS" RFL:RAMPLIST))
                         (cdr (assoc "INSIDESHOULDER" RFL:RAMPLIST))
                         (cdr (assoc "LANEWIDTH" RFL:RAMPLIST))
                      )
                      -1.0
                      D1
                      D2
                      (sin ANG)
                   )
                )
     )
     (setq OFFSET2 (+ (* D1
                         (+ (cdr (assoc "LANEOFFSET" RFL:RAMPLIST))
                            (cdr (assoc "NOSEOFFSET" RFL:RAMPLIST))
                            (cdr (assoc "NOSERADIUS" RFL:RAMPLIST))
                         )
                            )
                      (* (+ (cdr (assoc "NOSERADIUS" RFL:RAMPLIST))
                            (cdr (assoc "INSIDESHOULDER" RFL:RAMPLIST))
                            (cdr (assoc "LANEWIDTH" RFL:RAMPLIST))
                         )
                         D1
                         (cos ANG)
                      )
                   )
     )
     (setq OFFSET1 (* D1
                      (cdr (assoc "LANEOFFSET" RFL:RAMPLIST))
                   )
     )
     (setq STA1 (+ STA2
                   (* -1.0
                      D1
                      D2
                      (abs (- OFFSET2 OFFSET1))
                      (cdr (assoc "RAMPTAPER" RFL:RAMPLIST))
                   )
                )
     )
     (if (or (= nil (RFL:XY (list STA1 0.0)))
             (= nil (RFL:XY (list STA2 0.0)))
             (= nil (RFL:XY (list (cdr (assoc "NOSESTATION" RFL:RAMPLIST)) 0.0)))
         )
      (progn
;       (alert "!!!!!  Point not on alignment  !!!!!")
      )
      (progn
       (setq PL1 (RFL:XY (list STA2 OFFSET2)))
       (setq STA STA1)
       (setq OFFSET OFFSET1)
       (setq DSTA (/ (- STA2 STA1) (cdr (assoc "RAMPVERTICIES" RFL:RAMPLIST))))
       (setq DOFFSET (/ (- OFFSET2 OFFSET1) (cdr (assoc "RAMPVERTICIES" RFL:RAMPLIST))))
       (setq C 0)
;       (setq ENTLISTNEW (list (cons 0 "LWPOLYLINE")))
;       (setq ENTLISTNEW (append ENTLISTNEW (list (cons 90 (+ (cdr (assoc "RAMPVERTICIES" RFL:RAMPLIST)) 1)))))
;       (while (<= C (cdr (assoc "RAMPVERTICIES" RFL:RAMPLIST)))
;        (setq ENTLISTNEW (append ENTLISTNEW (list (append (list 10) (RFL:XY (list (+ STA1 (* C DSTA))
;                                                                                  (+ OFFSET1 (* C DOFFSET))))))))
;        (setq C (+ C 1))
;       )
;(setq xxx ENTLISTNEW)
;(exit)
;       (entmake)
;       (entmake ENTLISTNEW)
       (command "._PLINE")
       (while (<= C (cdr (assoc "RAMPVERTICIES" RFL:RAMPLIST)))
        (if (setq P (RFL:XY (list (+ STA1 (* C DSTA))
                                  (+ OFFSET1 (* C DOFFSET)))))
         (command P)
        )
        (setq C (+ C 1))
       )
       (command "")
       (ssadd (entlast) ENTSET)
       (setq STA (+ STA1
                    (* (cdr (assoc "WEAVEOFFSET" RFL:RAMPLIST))
                       (cdr (assoc "RAMPTAPER" RFL:RAMPLIST))
                       D1
                       D2
                    )
                 )
       )
       (command "._LINE"
                (RFL:XY (list STA
                              (* D1 (+ (cdr (assoc "WEAVEOFFSET" RFL:RAMPLIST))
                                       (cdr (assoc "LANEOFFSET" RFL:RAMPLIST))
                                    )
                              )
                        )
                )
                (RFL:XY (list STA
                              (* D1 (+ 20.0
                                       (cdr (assoc "WEAVEOFFSET" RFL:RAMPLIST))
                                       (cdr (assoc "LANEOFFSET" RFL:RAMPLIST))
                                    )
                              )
                        )
                )
                ""
       )
       (ssadd (entlast) ENTSET)
       (setvar "DIMZIN" 8)
       (if (= (cdr (assoc 40 (tblsearch "STYLE" (getvar "TEXTSTYLE")))) 0.0)
        (command "._TEXT"
                 "ML"
                 (RFL:XY (list STA
                               (* D1 (+ 20.0
                                        (cdr (assoc "WEAVEOFFSET" RFL:RAMPLIST))
                                        (cdr (assoc "LANEOFFSET" RFL:RAMPLIST))
                                     )
                               )
                         )
                 )
                 5.0
                 (RFL:XY (list STA
                               (* D1 (+ 50.0
                                        (cdr (assoc "WEAVEOFFSET" RFL:RAMPLIST))
                                        (cdr (assoc "LANEOFFSET" RFL:RAMPLIST))
                                     )
                               )
                         )
                 )
                 (if RFL:RAMPTAPERLABEL
                  (strcat "Weave (" (rtos (cdr (assoc "RAMPTAPER" RFL:RAMPLIST))) ":1 TAPER)")
                  (strcat "Weave: " (RFL:STATXT STA))
                 )
                 ;""
        )
        (command "._TEXT"
                 "ML"
                 (RFL:XY (list STA
                               (* D1 (+ 20.0
                                        (cdr (assoc "WEAVEOFFSET" RFL:RAMPLIST))
                                        (cdr (assoc "LANEOFFSET" RFL:RAMPLIST))
                                     )
                               )
                         )
                 )
                 (RFL:XY (list STA
                               (* D1 (+ 50.0
                                        (cdr (assoc "WEAVEOFFSET" RFL:RAMPLIST))
                                        (cdr (assoc "LANEOFFSET" RFL:RAMPLIST))
                                     )
                               )
                         )
                 )
                 (if RFL:RAMPTAPERLABEL
                  (strcat "Weave (" (rtos (cdr (assoc "RAMPTAPER" RFL:RAMPLIST))) ":1 TAPER)")
                  (strcat "Weave: " (RFL:STATXT STA))
                 )
                 ;""
        )
       )
       (ssadd (entlast) ENTSET)
       (setvar "DIMZIN" 0)
       (setq STA1 (+ STA1
                     (* (+ (cdr (assoc "TAPEROFFSET" RFL:RAMPLIST))
                           (cdr (assoc "GOREWIDTH" RFL:RAMPLIST))
                        )
                        (cdr (assoc "RAMPTAPER" RFL:RAMPLIST))
                        D1
                        D2
                     )
                  )
       )
       (setq OFFSET1 (* D1
                        (+ (cdr (assoc "LANEOFFSET" RFL:RAMPLIST))
                           (cdr (assoc "TAPEROFFSET" RFL:RAMPLIST))
                        )
                     )
       )
       (setq STA2 (+ (cdr (assoc "NOSESTATION" RFL:RAMPLIST))
                     (* (+ (cdr (assoc "NOSERADIUS" RFL:RAMPLIST))
                           (cdr (assoc "INSIDESHOULDER" RFL:RAMPLIST))
                        )
                        -1.0
                        D1
                        D2
                        (sin ANG)
                     )
                  )
       )
       (setq OFFSET2 (+ (* D1
                           (+ (cdr (assoc "LANEOFFSET" RFL:RAMPLIST))
                              (cdr (assoc "NOSEOFFSET" RFL:RAMPLIST))
                              (cdr (assoc "NOSERADIUS" RFL:RAMPLIST))
                           )
                        )
                        (* (+ (cdr (assoc "NOSERADIUS" RFL:RAMPLIST))
                              (cdr (assoc "INSIDESHOULDER" RFL:RAMPLIST))
                           )
                           D1
                           (cos ANG)
                        )
                     )
       )
       (setq STA STA1)
       (setq OFFSET OFFSET1)
       (setq DSTA (/ (- STA2 STA1) (cdr (assoc "INSIDEVERTICIES" RFL:RAMPLIST))))
       (setq DOFFSET (/ (- OFFSET2 OFFSET1) (cdr (assoc "INSIDEVERTICIES" RFL:RAMPLIST))))
       (setq C 0)
       (command "._PLINE")
       (if (> (cdr (assoc "TAPEROFFSET" RFL:RAMPLIST)) 0.0)
        (if (setq P (RFL:XY (list STA1
                                  (* D1 (cdr (assoc "LANEOFFSET" RFL:RAMPLIST)))
                            )
                    )
            )
         (command P)
        )
       )
       (while (<= C (cdr (assoc "INSIDEVERTICIES" RFL:RAMPLIST)))
        (if (setq P (RFL:XY (list (+ STA1 (* C DSTA))
                                  (+ OFFSET1 (* C DOFFSET)))))
         (command P)
        )
        (setq C (+ C 1))
       )
       (command "")
       (ssadd (entlast) ENTSET)
       (setq PL2 (RFL:XY (list (cdr (assoc "NOSESTATION" RFL:RAMPLIST))
                               (* D1
                                  (+ (cdr (assoc "LANEOFFSET" RFL:RAMPLIST))
                                     (cdr (assoc "NOSEOFFSET" RFL:RAMPLIST))
                                     (cdr (assoc "NOSERADIUS" RFL:RAMPLIST))
                                  )
                               )
                         )
                 )
       )
       (setq ANG2 (+ (angle PL1 PL2)
                     (* D2
                        (/ pi 2.0)
                     )
                  )
       )
       (setq PL2 (list (+ (car PL1)
                          (* 50.0
                             (cos ANG2)
                          )
                       )
                       (+ (cadr PL1)
                          (* 50.0
                             (sin ANG2)
                          )
                       )
                 )
       )
       (command "._LINE" PL1 PL2 "")
       (ssadd (entlast) ENTSET)
       (setvar "DIMZIN" 8)
       (if (= (cdr (assoc 40 (tblsearch "STYLE" (getvar "TEXTSTYLE")))) 0.0)
        (command "._TEXT"
                 "MR"
                 PL2
                 5.0
                 PL1
                 (strcat "R=" (rtos (abs NOSEALIGNRADIUS)))
                 ;""
        )
        (command "._TEXT"
                 "MR"
                 PL2
                 PL1
                 (strcat "R=" (rtos (abs NOSEALIGNRADIUS)))
                 ;""
        )
       )
       (ssadd (entlast) ENTSET)
       (setvar "DIMZIN" 0)
      )
     )      
     (if (> (cdr (assoc "RETURNOFFSET" RFL:RAMPLIST))
            (cdr (assoc "NOSEOFFSET" RFL:RAMPLIST))
         )
      (alert "!!!!!  Return offset greater than nose offset  !!!!!")
      (if (/= (cdr (assoc "RETURNOFFSET" RFL:RAMPLIST))
              (cdr (assoc "NOSEOFFSET" RFL:RAMPLIST))
          )
       (progn
        (setq ANG (atan (/ 1.0 (cdr (assoc "RETURNTAPER" RFL:RAMPLIST)))))
        (setq STA2 (+ (cdr (assoc "NOSESTATION" RFL:RAMPLIST))
                      (* (cdr (assoc "NOSERADIUS" RFL:RAMPLIST))
                         -1.0
                         D1
                         D2
                         (sin ANG)
                      )
                   )
        )
        (setq OFFSET2 (- (* D1
                            (+ (cdr (assoc "LANEOFFSET" RFL:RAMPLIST))
                               (cdr (assoc "NOSEOFFSET" RFL:RAMPLIST))
                               (cdr (assoc "NOSERADIUS" RFL:RAMPLIST))
                            )
                         )
                         (* (cdr (assoc "NOSERADIUS" RFL:RAMPLIST))
                            D1
                            (cos ANG)
                         )
                      )
        )
        (setq OFFSET1 (* D1
                         (+ (cdr (assoc "LANEOFFSET" RFL:RAMPLIST))
                            (cdr (assoc "RETURNOFFSET" RFL:RAMPLIST))
                         )
                      )
        )
        (setq STA1 (+ STA2
                      (* D1
                         D2
                         (abs (- OFFSET2 OFFSET1))
                         (cdr (assoc "RETURNTAPER" RFL:RAMPLIST))
                      )
                   )
        )
        (if (or (= nil (RFL:XY (list STA1 0.0)))
                (= nil (RFL:XY (list STA2 0.0)))
            )
         (alert "!!!!!  Point not on alignment  !!!!!")
         (progn
          (setq STA STA1)
          (setq OFFSET OFFSET1)
          (setq DSTA (/ (- STA2 STA1) (cdr (assoc "RETURNVERTICIES" RFL:RAMPLIST))))
          (setq DOFFSET (/ (- OFFSET2 OFFSET1) (cdr (assoc "RETURNVERTICIES" RFL:RAMPLIST))))
          (setq C 0)
          (command "._PLINE")
          (while (<= C (cdr (assoc "RETURNVERTICIES" RFL:RAMPLIST)))
           (if (setq P (RFL:XY (list (+ STA1 (* C DSTA))
                                     (+ OFFSET1 (* C DOFFSET)))))
            (command P)
           )
           (setq C (+ C 1))
          )
          (command "")
          (ssadd (entlast) ENTSET)
         )
        )
       )
      )
     )
     (RFL:RAMPPUTXDATA ENTNOSE ENTSET)
    )
   )
  )
 )
 
 (setq RFL:RAMPLIST ALSAVE)
 
 (setvar "CMDECHO" CMDECHO)
 (setvar "ANGBASE" ANGBASE)
 (setvar "ANGDIR" ANGDIR)
 (setvar "CLAYER" CLAYER)
 (setvar "DIMZIN" DIMZIN)
 (setvar "OSMODE" OSMODE)
 (setvar "ORTHOMODE" ORTHOMODE)
 (setvar "PLINETYPE" PLINETYPE)
 (setq RFL:ALIGNLIST ALSAVE)
 (setq RFL:RAMPLIST RLSAVE)
 nil
)
(defun RFL:RAMPPUTXDATA (ENT ENTSET / ALIGNDATALIST C CMIN CMAX ENTLIST ENTDATALIST MAXNODES RAMPDATALIST STA)
 (setq MAXNODES 100)
 (vl-load-com)
 (regapp "RFLTOOLS_XENT")
 (setq RAMPDATALIST (list (cons 1000 "RFLTOOLS_RAMP_NOSE")
                          (cons 1040 (cdr (assoc "LANEOFFSET" RFL:RAMPLIST)))
                          (cons 1040 (cdr (assoc "RAMPTAPER" RFL:RAMPLIST)))
                          (cons 1040 (cdr (assoc "RAMPTAPERENTRANCE" RFL:RAMPLIST)))
                          (cons 1040 (cdr (assoc "RAMPTAPEREXIT" RFL:RAMPLIST)))
                          (cons 1070 (cdr (assoc "RAMPVERTICIES" RFL:RAMPLIST)))
                          (cons 1040 (cdr (assoc "WEAVEOFFSET" RFL:RAMPLIST)))
                          (cons 1040 (cdr (assoc "WEAVEOFFSETENTRANCESINGLE" RFL:RAMPLIST)))
                          (cons 1040 (cdr (assoc "WEAVEOFFSETENTRANCEDUAL" RFL:RAMPLIST)))
                          (cons 1040 (cdr (assoc "WEAVEOFFSETEXITSINGLE" RFL:RAMPLIST)))
                          (cons 1040 (cdr (assoc "WEAVEOFFSETEXITDUAL" RFL:RAMPLIST)))
                          (cons 1040 (cdr (assoc "GOREWIDTH" RFL:RAMPLIST)))
                          (cons 1040 (cdr (assoc "GOREWIDTHENTRANCESINGLE" RFL:RAMPLIST)))
                          (cons 1040 (cdr (assoc "GOREWIDTHENTRANCEDUAL" RFL:RAMPLIST)))
                          (cons 1040 (cdr (assoc "GOREWIDTHEXITSINGLE" RFL:RAMPLIST)))
                          (cons 1040 (cdr (assoc "GOREWIDTHEXITDUAL" RFL:RAMPLIST)))
                          (cons 1040 (cdr (assoc "TAPEROFFSET" RFL:RAMPLIST)))
                          (cons 1040 (cdr (assoc "TAPEROFFSETENTRANCE" RFL:RAMPLIST)))
                          (cons 1040 (cdr (assoc "TAPEROFFSETEXIT" RFL:RAMPLIST)))
                          (cons 1070 (cdr (assoc "INSIDEVERTICIES" RFL:RAMPLIST)))
                          (cons 1040 (cdr (assoc "NOSESTATION" RFL:RAMPLIST)))
                          (cons 1040 (cdr (assoc "NOSEOFFSET" RFL:RAMPLIST)))
                          (cons 1040 (cdr (assoc "NOSERADIUS" RFL:RAMPLIST)))
                          (cons 1040 (cdr (assoc "NOSERADIUSENTRANCE" RFL:RAMPLIST)))
                          (cons 1040 (cdr (assoc "NOSERADIUSEXIT" RFL:RAMPLIST)))
                          (cons 1040 (cdr (assoc "INSIDESHOULDER" RFL:RAMPLIST)))
                          (cons 1040 (cdr (assoc "INSIDESHOULDERSINGLE" RFL:RAMPLIST)))
                          (cons 1040 (cdr (assoc "INSIDESHOULDERDUAL" RFL:RAMPLIST)))
                          (cons 1040 (cdr (assoc "LANEWIDTH" RFL:RAMPLIST)))
                          (cons 1040 (cdr (assoc "LANEWIDTHSINGLE" RFL:RAMPLIST)))
                          (cons 1040 (cdr (assoc "LANEWIDTHDUAL" RFL:RAMPLIST)))
                          (cons 1040 (cdr (assoc "RETURNTAPER" RFL:RAMPLIST)))
                          (cons 1040 (cdr (assoc "RETURNOFFSET" RFL:RAMPLIST)))
                          (cons 1070 (cdr (assoc "RETURNVERTICIES" RFL:RAMPLIST)))
                          (cons 1000 (cdr (assoc "SINGLELANE" RFL:RAMPLIST)))
                          (cons 1000 (cdr (assoc "DUALLANE" RFL:RAMPLIST)))
                          (cons 1000 (cdr (assoc "UPCHAINAGE" RFL:RAMPLIST)))
                          (cons 1000 (cdr (assoc "DOWNCHAINAGE" RFL:RAMPLIST)))
                          (cons 1000 (cdr (assoc "RIGHTSIDE" RFL:RAMPLIST)))
                          (cons 1000 (cdr (assoc "LEFTSIDE" RFL:RAMPLIST)))
                          (cons 1000 (cdr (assoc "EXITTERMINAL" RFL:RAMPLIST)))
                          (cons 1000 (cdr (assoc "ENTRANCETERMINAL" RFL:RAMPLIST)))
                    )
 )
 (setq STA (cdr (assoc "NOSESTATION" RFL:RAMPLIST)))
 (if (> MAXNODES (length RFL:ALIGNLIST))
  (progn
   (setq CMIN 0)
   (setq CMAX (length RFL:ALIGNLIST))
  )
  (progn
   (setq C 0)
   (while (> STA (car (nth C RFL:ALIGNLIST)))
    (setq C (+ C 1))
   )
   (setq CMIN (max (- C (/ MAXNODES 2)) 0))
   (setq CMAX (min (+ C (/ MAXNODES 2)) (length RFL:ALIGNLIST)))
   (if (= CMIN 0)
    (setq CMAX (+ CMIN MAXNODES))
    (if (= CMAX (length RFL:ALIGNLIST))
     (setq CMIN (- CMAX MAXNODES))
    )
   )
  )
 )
 (setq ALIGNDATALIST (list (cons 1000 "#RFL HORIZONTAL ALIGNMENT FILE")))
 (setq C CMIN)
 (while (< C CMAX)
  (setq ALIGNDATALIST (append ALIGNDATALIST (list (cons 1040 (nth 0 (nth C RFL:ALIGNLIST))))))
  (setq ALIGNDATALIST (append ALIGNDATALIST (list (cons 1040 (nth 0 (nth 1 (nth C RFL:ALIGNLIST)))))))
  (setq ALIGNDATALIST (append ALIGNDATALIST (list (cons 1040 (nth 1 (nth 1 (nth C RFL:ALIGNLIST)))))))
  (setq ALIGNDATALIST (append ALIGNDATALIST (list (cons 1040 (nth 0 (nth 2 (nth C RFL:ALIGNLIST)))))))
  (setq ALIGNDATALIST (append ALIGNDATALIST (list (cons 1040 (nth 1 (nth 2 (nth C RFL:ALIGNLIST)))))))
  (if (listp (nth 3 (nth C RFL:ALIGNLIST)))
   (progn
    (setq ALIGNDATALIST (append ALIGNDATALIST (list (cons 1000 "SPIRAL"))))
	(setq ALIGNDATALIST (append ALIGNDATALIST (list (cons 1040 (nth 0 (nth 0 (nth 3 (nth C RFL:ALIGNLIST))))))))
	(setq ALIGNDATALIST (append ALIGNDATALIST (list (cons 1040 (nth 1 (nth 0 (nth 3 (nth C RFL:ALIGNLIST))))))))
	(setq ALIGNDATALIST (append ALIGNDATALIST (list (cons 1040 (nth 0 (nth 1 (nth 3 (nth C RFL:ALIGNLIST))))))))
	(setq ALIGNDATALIST (append ALIGNDATALIST (list (cons 1040 (nth 1 (nth 1 (nth 3 (nth C RFL:ALIGNLIST))))))))
	(setq ALIGNDATALIST (append ALIGNDATALIST (list (cons 1040 (nth 0 (nth 2 (nth 3 (nth C RFL:ALIGNLIST))))))))
	(setq ALIGNDATALIST (append ALIGNDATALIST (list (cons 1040 (nth 1 (nth 2 (nth 3 (nth C RFL:ALIGNLIST))))))))
	(setq ALIGNDATALIST (append ALIGNDATALIST (list (cons 1040 (nth 3 (nth 3 (nth C RFL:ALIGNLIST)))))))
   )
   (progn
    (setq ALIGNDATALIST (append ALIGNDATALIST (list (cons 1040 (nth 3 (nth C RFL:ALIGNLIST))))))
   )
  )
  (setq C (+ C 1))
 )
 (setq ALIGNDATALIST (append ALIGNDATALIST (list (cons 1000 "#END DEFINITION"))))
 (setq ENTDATALIST (list (cons 1000 "RFLTOOLS_RAMP_ENTITIES")))
 (if (/= nil ENTSET)
  (progn
   (setq C 0)
   (while (< C (sslength ENTSET))
    (setq ENTDATALIST (append ENTDATALIST (list (cons 1005 (cdr (assoc 5 (entget (ssname ENTSET C))))))))
    (setq C (+ C 1))
   )
  )
 )
 (setq ENTLIST (append (entget ENT)
                       (list
                             (list -3
                                   (append (list "RFLTOOLS_XENT")
                                           RAMPDATALIST
                                           ALIGNDATALIST
                                           ENTDATALIST
                                   )
                             )
                       )
               )
 )
 (entmod ENTLIST)
)
(defun RFL:RAMPGETENT (ENT / ENT2 ENTLIST ENTSET NODE)
 (setq ENTSET (ssadd))
 (setq ENTLIST (cdadr (assoc -3 (entget ENT (list "RFLTOOLS_XENT")))))
 (foreach NODE ENTLIST
  (progn
   (if (= 1005 (car NODE))
    (if (/= nil (setq ENT2 (handent (cdr NODE))))
     (ssadd ENT2 ENTSET)
    )
   )
  )
 )
 (setq ENTSET ENTSET)
)
(defun RFL:RAMPGETRAMP (ENT / ENTLIST ENTSET RFL:RAMPLIST)
 (setq RFL:RAMPLIST nil)
 (setq ENTLIST (cdadr (assoc -3 (entget ENT (list "RFLTOOLS_XENT")))))
 (if (/= (cdar ENTLIST) "RFLTOOLS_RAMP_NOSE")
  (princ "\n*** NO NOSE DATA FOUND ***")
  (progn
   (setq ENTLIST (cdr ENTLIST))
   (setq RFL:RAMPLIST (append RFL:RAMPLIST (list (cons "LANEOFFSET" (cdar ENTLIST)))))
   (setq ENTLIST (cdr ENTLIST))
   (setq RFL:RAMPLIST (append RFL:RAMPLIST (list (cons "RAMPTAPER" (cdar ENTLIST)))))
   (setq ENTLIST (cdr ENTLIST))
   (setq RFL:RAMPLIST (append RFL:RAMPLIST (list (cons "RAMPTAPERENTRANCE" (cdar ENTLIST)))))
   (setq ENTLIST (cdr ENTLIST))
   (setq RFL:RAMPLIST (append RFL:RAMPLIST (list (cons "RAMPTAPEREXIT" (cdar ENTLIST)))))
   (setq ENTLIST (cdr ENTLIST))
   (setq RFL:RAMPLIST (append RFL:RAMPLIST (list (cons "RAMPVERTICIES" (cdar ENTLIST)))))
   (setq ENTLIST (cdr ENTLIST))
   (setq RFL:RAMPLIST (append RFL:RAMPLIST (list (cons "WEAVEOFFSET" (cdar ENTLIST)))))
   (setq ENTLIST (cdr ENTLIST))
   (setq RFL:RAMPLIST (append RFL:RAMPLIST (list (cons "WEAVEOFFSETENTRANCESINGLE" (cdar ENTLIST)))))
   (setq ENTLIST (cdr ENTLIST))
   (setq RFL:RAMPLIST (append RFL:RAMPLIST (list (cons "WEAVEOFFSETENTRANCEDUAL" (cdar ENTLIST)))))
   (setq ENTLIST (cdr ENTLIST))
   (setq RFL:RAMPLIST (append RFL:RAMPLIST (list (cons "WEAVEOFFSETEXITSINGLE" (cdar ENTLIST)))))
   (setq ENTLIST (cdr ENTLIST))
   (setq RFL:RAMPLIST (append RFL:RAMPLIST (list (cons "WEAVEOFFSETEXITDUAL" (cdar ENTLIST)))))
   (setq ENTLIST (cdr ENTLIST))
   (setq RFL:RAMPLIST (append RFL:RAMPLIST (list (cons "GOREWIDTH" (cdar ENTLIST)))))
   (setq ENTLIST (cdr ENTLIST))
   (setq RFL:RAMPLIST (append RFL:RAMPLIST (list (cons "GOREWIDTHENTRANCESINGLE" (cdar ENTLIST)))))
   (setq ENTLIST (cdr ENTLIST))
   (setq RFL:RAMPLIST (append RFL:RAMPLIST (list (cons "GOREWIDTHENTRANCEDUAL" (cdar ENTLIST)))))
   (setq ENTLIST (cdr ENTLIST))
   (setq RFL:RAMPLIST (append RFL:RAMPLIST (list (cons "GOREWIDTHEXITSINGLE" (cdar ENTLIST)))))
   (setq ENTLIST (cdr ENTLIST))
   (setq RFL:RAMPLIST (append RFL:RAMPLIST (list (cons "GOREWIDTHEXITDUAL" (cdar ENTLIST)))))
   (setq ENTLIST (cdr ENTLIST))
   (setq RFL:RAMPLIST (append RFL:RAMPLIST (list (cons "TAPEROFFSET" (cdar ENTLIST)))))
   (setq ENTLIST (cdr ENTLIST))
   (setq RFL:RAMPLIST (append RFL:RAMPLIST (list (cons "TAPEROFFSETENTRANCE" (cdar ENTLIST)))))
   (setq ENTLIST (cdr ENTLIST))
   (setq RFL:RAMPLIST (append RFL:RAMPLIST (list (cons "TAPEROFFSETEXIT" (cdar ENTLIST)))))
   (setq ENTLIST (cdr ENTLIST))
   (setq RFL:RAMPLIST (append RFL:RAMPLIST (list (cons "INSIDEVERTICIES" (cdar ENTLIST)))))
   (setq ENTLIST (cdr ENTLIST))
   (setq RFL:RAMPLIST (append RFL:RAMPLIST (list (cons "NOSESTATION" (cdar ENTLIST)))))
   (setq ENTLIST (cdr ENTLIST))
   (setq RFL:RAMPLIST (append RFL:RAMPLIST (list (cons "NOSEOFFSET" (cdar ENTLIST)))))
   (setq ENTLIST (cdr ENTLIST))
   (setq RFL:RAMPLIST (append RFL:RAMPLIST (list (cons "NOSERADIUS" (cdar ENTLIST)))))
   (setq ENTLIST (cdr ENTLIST))
   (setq RFL:RAMPLIST (append RFL:RAMPLIST (list (cons "NOSERADIUSENTRANCE" (cdar ENTLIST)))))
   (setq ENTLIST (cdr ENTLIST))
   (setq RFL:RAMPLIST (append RFL:RAMPLIST (list (cons "NOSERADIUSEXIT" (cdar ENTLIST)))))
   (setq ENTLIST (cdr ENTLIST))
   (setq RFL:RAMPLIST (append RFL:RAMPLIST (list (cons "INSIDESHOULDER" (cdar ENTLIST)))))
   (setq ENTLIST (cdr ENTLIST))
   (setq RFL:RAMPLIST (append RFL:RAMPLIST (list (cons "INSIDESHOULDERSINGLE" (cdar ENTLIST)))))
   (setq ENTLIST (cdr ENTLIST))
   (setq RFL:RAMPLIST (append RFL:RAMPLIST (list (cons "INSIDESHOULDERDUAL" (cdar ENTLIST)))))
   (setq ENTLIST (cdr ENTLIST))
   (setq RFL:RAMPLIST (append RFL:RAMPLIST (list (cons "LANEWIDTH" (cdar ENTLIST)))))
   (setq ENTLIST (cdr ENTLIST))
   (setq RFL:RAMPLIST (append RFL:RAMPLIST (list (cons "LANEWIDTHSINGLE" (cdar ENTLIST)))))
   (setq ENTLIST (cdr ENTLIST))
   (setq RFL:RAMPLIST (append RFL:RAMPLIST (list (cons "LANEWIDTHDUAL" (cdar ENTLIST)))))
   (setq ENTLIST (cdr ENTLIST))
   (setq RFL:RAMPLIST (append RFL:RAMPLIST (list (cons "RETURNTAPER" (cdar ENTLIST)))))
   (setq ENTLIST (cdr ENTLIST))
   (setq RFL:RAMPLIST (append RFL:RAMPLIST (list (cons "RETURNOFFSET" (cdar ENTLIST)))))
   (setq ENTLIST (cdr ENTLIST))
   (setq RFL:RAMPLIST (append RFL:RAMPLIST (list (cons "RETURNVERTICIES" (cdar ENTLIST)))))
   (setq ENTLIST (cdr ENTLIST))
   (setq RFL:RAMPLIST (append RFL:RAMPLIST (list (cons "SINGLELANE" (cdar ENTLIST)))))
   (setq ENTLIST (cdr ENTLIST))
   (setq RFL:RAMPLIST (append RFL:RAMPLIST (list (cons "DUALLANE" (cdar ENTLIST)))))
   (setq ENTLIST (cdr ENTLIST))
   (setq RFL:RAMPLIST (append RFL:RAMPLIST (list (cons "UPCHAINAGE" (cdar ENTLIST)))))
   (setq ENTLIST (cdr ENTLIST))
   (setq RFL:RAMPLIST (append RFL:RAMPLIST (list (cons "DOWNCHAINAGE" (cdar ENTLIST)))))
   (setq ENTLIST (cdr ENTLIST))
   (setq RFL:RAMPLIST (append RFL:RAMPLIST (list (cons "RIGHTSIDE" (cdar ENTLIST)))))
   (setq ENTLIST (cdr ENTLIST))
   (setq RFL:RAMPLIST (append RFL:RAMPLIST (list (cons "LEFTSIDE" (cdar ENTLIST)))))
   (setq ENTLIST (cdr ENTLIST))
   (setq RFL:RAMPLIST (append RFL:RAMPLIST (list (cons "EXITTERMINAL" (cdar ENTLIST)))))
   (setq ENTLIST (cdr ENTLIST))
   (setq RFL:RAMPLIST (append RFL:RAMPLIST (list (cons "ENTRANCETERMINAL" (cdar ENTLIST)))))
   (setq ENTLIST (cdr ENTLIST))
   (setq RAMPENTLIST nil)
   (while (/= ENTLIST nil)
    (setq RAMPENTLIST (append RAMPENTLIST (list (cdar ENTLIST))))
    (setq ENTLIST (cdr ENTLIST))
   )
  )
 )
 RFL:RAMPLIST
)
(defun RFL:RAMPGETALIGN (ENT / RFL:ALIGNLIST BULGE ENTLIST LO P1X P1Y P2X P2Y PLTX PLTY PLTSTX PLTSTY PSTX PSTY STA)
 (setq RFL:ALIGNLIST nil)
 (setq ENTLIST (cdadr (assoc -3 (entget ENT (list "RFLTOOLS_XENT")))))
 (while (and (/= ENTLIST nil) (/= (cdar ENTLIST) "#RFL HORIZONTAL ALIGNMENT FILE"))
  (setq ENTLIST (cdr ENTLIST))
 )
 (setq ENTLIST (cdr ENTLIST))
 (while (and (/= ENTLIST nil) (/= (cdar ENTLIST) "#END DEFINITION"))
  (setq STA (cdar ENTLIST))
  (setq ENTLIST (cdr ENTLIST))
  (setq P1X (cdar ENTLIST))
  (setq ENTLIST (cdr ENTLIST))
  (setq P1Y (cdar ENTLIST))
  (setq ENTLIST (cdr ENTLIST))
  (setq P2X (cdar ENTLIST))
  (setq ENTLIST (cdr ENTLIST))
  (setq P2Y (cdar ENTLIST))
  (setq ENTLIST (cdr ENTLIST))
  (if (= (cdar ENTLIST) "SPIRAL")
   (progn
    (setq ENTLIST (cdr ENTLIST))
    (setq PLTX (cdar ENTLIST))
    (setq ENTLIST (cdr ENTLIST))
    (setq PLTY (cdar ENTLIST))
    (setq ENTLIST (cdr ENTLIST))
    (setq PLTSTX (cdar ENTLIST))
    (setq ENTLIST (cdr ENTLIST))
    (setq PLTSTY (cdar ENTLIST))
    (setq ENTLIST (cdr ENTLIST))
    (setq PSTX (cdar ENTLIST))
    (setq ENTLIST (cdr ENTLIST))
    (setq PSTY (cdar ENTLIST))
    (setq ENTLIST (cdr ENTLIST))
    (setq LO (cdar ENTLIST))
    (setq BULGE (list (list PLTX PLTY) (list PLTSTX PLTSTY) (list PSTX PSTY) LO))
   )
   (progn
    (setq BULGE (cdar ENTLIST))
   )
  )
  (setq ENTLIST (cdr ENTLIST))
  (setq RFL:ALIGNLIST (append RFL:ALIGNLIST (list (list STA (list P1X P1Y) (list P2X P2Y) BULGE))))
 )
 RFL:ALIGNLIST
)
(defun C:MOVENOSE (/ *error* ALSAVE ENTNOSE ENTNOSELIST ENTSET GRCODE P P1 RLSAVE REP)
 (setq RLSAVE RFL:RAMPLIST)
 (setq ALSAVE RFL:ALIGNLIST)

 (defun *error* (msg)
  (setq RFL:ALIGNLIST ALSAVE)
  (setq RFL:RAMPLIST RLSAVE)
  ;(setq *error* nil)
  (print msg)
 )

 (setq ENTNOSE (car (entsel "\nSelect Nose : ")))
 (if (= nil (RFL:RAMPGETRAMP ENTNOSE))
  (princ "\n*** Entity does not contain RAMP information ***")
  (progn
   (setq ENTNOSELIST (entget ENTNOSE))
   (setq RFL:ALIGNLIST (RFL:RAMPGETALIGN ENTNOSE))
   (setq REP "")
   (while (or (= (car (setq GRCODE (grread t 15 0))) 5) (= (car GRCODE) 2))
    (cond ((= (car GRCODE) 2)
           (progn
            (princ (chr (cadr GRCODE)))
           )
          )
          ((= (car GRCODE) 5)
           (progn
            (setq P (cadr GRCODE))
            (setq P1 (RFL:STAOFF P))
            (if (/= nil P1)
             (progn
              (setq P1 (RFL:XY (list (car P1) 0.0)))
;              (grdraw P1 P -1)
              (setq ENTNOSELIST (subst (append (list 10) P1) (assoc 10 ENTNOSELIST) ENTNOSELIST))
              (entmod ENTNOSELIST)
              (entupd ENTNOSE)
              (RFL:RAMPDRAW ENTNOSE 7)
             )
            )
           )
          )
    )
   )
  )
 )
 (setq RFL:RAMPLIST RLSAVE)
 (setq RFL:ALIGNLIST ALSAVE)
 nil
)
(defun C:UPDATENOSE (/ ALSAVE ENTNOSE RLSAVE)
 (command "._UNDO" "M")
 (setq RLSAVE RFL:RAMPLIST)
 (setq ALSAVE RFL:ALIGNLIST)
 (setq ENTNOSE (car (entsel "\nSelect Nose : ")))
 (if (= nil (RFL:RAMPGETRAMP ENTNOSE))
  (princ "\n*** Entity does not contain RAMP information ***")
  (progn
   (RFL:RAMPDRAW ENTNOSE 7)
  )
 )
 (setq RFL:RAMPLIST RLSAVE)
 (setq RFL:ALIGNLIST ALSAVE)
 nil
)
(defun C:SETNOSE (/ ENTNOSE)
 (setq ENTNOSE (car (entsel "\nSelect Nose : ")))
 (if (= nil (RFL:RAMPGETRAMP ENTNOSE))
  (princ "\n*** Entity does not contain RAMP information ***")
  (progn
   (setq RFL:ALIGNLIST (RFL:RAMPGETALIGN ENTNOSE))
   (setq RFL:RAMPLIST (RFL:RAMPGETRAMP ENTNOSE))
   nil
  )
 )
)
(defun C:ERASENOSE (/ ENTNOSE RAMPENTSET)
 (command "._UNDO" "M")
 (setq ENTNOSE (car (entsel "\nSelect Nose : ")))
 (if (= nil (RFL:RAMPGETRAMP ENTNOSE))
  (princ "\n*** Entity does not contain RAMP information ***")
  (progn
   (setq RAMPENTSET (RFL:RAMPGETENT ENTNOSE))
   (ssadd ENTNOSE RAMPENTSET)
   (command "._ERASE" RAMPENTSET "")
   nil
  )
 )
)
