;
;
;     Program written by Robert Livingston, 2014-11-24
;
;     C:GPROFOGC3D extracts the existing ground profile of the currently defined alignment from a C3D surface
;
;
(defun C:GPROFOGC3D (/ *error* ALSAVE ANG ANGBASE ANGDIR ATOTAL C CMAX CMDECHO L LSTEP NODE NODE2 OBSURFACE OS OSTOL P1 P2 R TMP TMPLIST TOL XYOGLIST)
;(defun C:GPROFOGC3D ()
 (setq CMDECHO (getvar "CMDECHO"))
 (setvar "CMDECHO" 0)
 (setq ANGBASE (getvar "ANGBASE"))
 (setvar "ANGBASE" 0)
 (setq ANGDIR (getvar "ANGDIR"))
 (setvar "ANGDIR" 0)
 (setq ALSAVE RFL:ALIGNLIST)
 
 (setq TOL 0.00000001)
 (setq OSTOL 0.1)
 
 (defun *error* (msg)
  (setvar "CMDECHO" CMDECHO)
  (setvar "ANGBASE" ANGBASE)
  (setvar "ANGDIR" ANGDIR)
  (setq RFL:ALIGNLIST ALSAVE)
  ;(setq *error* nil)
  (print msg)
 )

 (defun DIST (P1 P2 BULGE / ATOTAL CHORD R)
  (setq ATOTAL (* 4 (atan (abs BULGE))))
  (setq CHORD (distance P1 P2))
  (if (= 0.0 BULGE)
   (eval CHORD)
   (progn 
    (setq R (/ CHORD (* 2 (sin (/ ATOTAL 2)))))
    (* R ATOTAL)
   )
  )
 )
 
 (command ".UNDO" "M")

 (if (= nil RFL:ALIGNLIST)
  (princ "\n*** Alignment not defined ***")
  (progn
   (setq OBSURFACE (RFL:GETC3DSURFACE))
   (if (= nil OBSURFACE)
    (princ "\n*** Error getting C3D Surface ***")
    (progn
     (if (= (setq OS (getreal "\nOffset (<return> = 0.0) : ")) nil) (setq OS 0.0))
     (setq XYOGLIST nil)
     (setq RFL:OGLIST nil)
     (foreach NODE ALSAVE
      (progn
       (if (listp (last NODE))
        (progn ; SPIRAL
         (setq XYOGLIST nil)
         (setq R (RFL:GETSPIRALR2 (nth 0 (last NODE)) (nth 1 (last NODE)) (nth 2 (last NODE))))
         (setq L (RFL:GETSPIRALLS2 (nth 0 (last NODE)) (nth 1 (last NODE)) (nth 2 (last NODE))))
         (if (not (listp (last (last NODE))))
          (setq L (- L (last (last NODE))))
         )
         (setq ANG (atan (/ (sqrt (- (* 2.0 R OSTOL) (* OSTOL OSTOL))) (- R OSTOL))))
         (setq LSTEP (* 2.0 R ANG))
         (setq CMAX (+ 1 (fix (/ L LSTEP))))
         (setq LSTEP (/ L CMAX))
         (setq RFL:ALIGNLIST (list (list 0.0 (nth 1 NODE) (nth 2 NODE) (nth 3 NODE))))
         ;(setq P1 (nth 1 NODE))
         (setq P1 (RFL:XY (list 0.0 OS)))
         (setq C 1)
         (while (< C CMAX)
          ;(setq P2 (RFL:XY (list (* C LSTEP) 0.0)))
          (setq P2 (RFL:XY (list (* C LSTEP) OS)))
          (if (/= nil (setq TMPLIST (RFL:GETSURFACELINE P1 P2 OBSURFACE)))
           (if (= nil XYOGLIST)
            (setq XYOGLIST (append XYOGLIST TMPLIST))
            (setq XYOGLIST (append XYOGLIST (cdr TMPLIST)))
           )
          )
          (setq C (+ C 1))
          (setq P1 P2)
         )
         ;(setq P2 (nth 2 NODE))
         (setq P2 (RFL:XY (list L OS)))
         (if (/= nil (setq TMPLIST (RFL:GETSURFACELINE P1 P2 OBSURFACE)))
          (if (= nil XYOGLIST)
           (setq XYOGLIST (append XYOGLIST TMPLIST))
           (setq XYOGLIST (append XYOGLIST (cdr TMPLIST)))
          )
         )
         (setq RFL:ALIGNLIST (list NODE))
         (foreach NODE2 XYOGLIST
          (progn
           (setq TMP (RFL:STAOFF (list (car NODE2) (cadr NODE2))))
           (if (/= nil TMP)
            (setq RFL:OGLIST (append RFL:OGLIST (list (list (car TMP) (last NODE2)))))
           )
          )
         )
        )
        (if (< (abs (last NODE)) TOL)
         (progn ; LINE
          (setq XYOGLIST nil)
          ;(setq P1 (nth 1 NODE))
          ;(setq P2 (nth 2 NODE))
          (setq RFL:ALIGNLIST (list (list 0.0 (nth 1 NODE) (nth 2 NODE) (nth 3 NODE))))
          (setq L (distance (nth 1 NODE) (nth 2 NODE)))
          (setq P1 (RFL:XY (list 0.0 OS)))
          (setq P2 (RFL:XY (list L OS)))
          (if (/= nil (setq TMPLIST (RFL:GETSURFACELINE P1 P2 OBSURFACE)))
           (if (= nil XYOGLIST)
            (setq XYOGLIST (append XYOGLIST TMPLIST))
            (setq XYOGLIST (append XYOGLIST (cdr TMPLIST)))
           )
          )
          (setq RFL:ALIGNLIST (list NODE))
          (foreach NODE2 XYOGLIST
           (progn
            (setq TMP (RFL:STAOFF (list (car NODE2) (cadr NODE2))))
            (if (/= nil TMP)
             (setq RFL:OGLIST (append RFL:OGLIST (list (list (car TMP) (last NODE2)))))
            )
           )
          )
         )
         (progn ; ARC
          (setq XYOGLIST nil)
          (setq R (RFL:RADIUS (nth 1 NODE) (nth 2 NODE) (nth 3 NODE)))
          (setq ATOTAL (* 4 (atan (abs (nth 3 NODE)))))
          (setq L (* R ATOTAL))
          (setq ANG (atan (/ (sqrt (- (* 2.0 R OSTOL) (* OSTOL OSTOL))) (- R OSTOL))))
          (setq LSTEP (* 2.0 R ANG))
          (setq CMAX (+ 1 (fix (/ L LSTEP))))
          (setq LSTEP (/ L CMAX))
          (setq RFL:ALIGNLIST (list (list 0.0 (nth 1 NODE) (nth 2 NODE) (nth 3 NODE))))
          ;(setq P1 (nth 1 NODE))
          (setq P1 (RFL:XY (list 0.0 OS)))
          (setq C 1)
          (while (< C CMAX)
           ;(setq P2 (RFL:XY (list (* C LSTEP) 0.0)))
           (setq P2 (RFL:XY (list (* C LSTEP) OS)))
           (if (/= nil (setq TMPLIST (RFL:GETSURFACELINE P1 P2 OBSURFACE)))
            (if (= nil XYOGLIST)
             (setq XYOGLIST (append XYOGLIST TMPLIST))
             (setq XYOGLIST (append XYOGLIST (cdr TMPLIST)))
            )
           )
           (setq C (+ C 1))
           (setq P1 P2)
          )
          ;(setq P2 (nth 2 NODE))
          (setq P2 (RFL:XY (list L OS)))
          (if (/= nil (setq TMPLIST (RFL:GETSURFACELINE P1 P2 OBSURFACE)))
           (if (= nil XYOGLIST)
            (setq XYOGLIST (append XYOGLIST TMPLIST))
            (setq XYOGLIST (append XYOGLIST (cdr TMPLIST)))
           )
          )
          (setq RFL:ALIGNLIST (list NODE))
          (foreach NODE2 XYOGLIST
           (progn
            (setq TMP (RFL:STAOFF (list (car NODE2) (cadr NODE2))))
            (if (/= nil TMP)
             (setq RFL:OGLIST (append RFL:OGLIST (list (list (car TMP) (last NODE2)))))
            )
           )
          )
         )
        )
       )
      )
     )
;     (if (/= nil XYOGLIST)
;      (progn
;       (setq RFL:ALIGNLIST ALSAVE)
;       (setq TMPLIST XYOGLIST)
;       (setq XYOGLIST nil)
;       (foreach NODE TMPLIST
;        (progn
;         (setq TMP (RFL:STAOFF (list (car NODE) (cadr NODE))))
;         (if (/= nil TMP)
;          (setq XYOGLIST (append XYOGLIST (list (list (car TMP) (last NODE)))))
;         )
;        )
;       )
;      )
;     )
    )
   )
  )
 )

 (setvar "CMDECHO" CMDECHO)
 (setvar "ANGBASE" ANGBASE)
 (setvar "ANGDIR" ANGDIR)
 (setq RFL:ALIGNLIST ALSAVE)
 (eval nil)
)
