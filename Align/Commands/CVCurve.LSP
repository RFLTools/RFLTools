(defun C:VCURVE (/ A ACTIVEDOC ACTIVESPACE B C CMDECHO D ENT ENTLIST G G1 G2 P P1 P2 P3 P4 PP
                   OSMODE TMP VEXAG X Y Z)
 (setq CMDECHO (getvar "CMDECHO"))
 (setvar "CMDECHO" 0)
 (setq OSMODE (getvar "OSMODE"))

 (vl-load-com)
 (setq ACTIVEDOC (vla-get-activedocument (vlax-get-acad-object)))
 (setq ACTIVESPC
       (vlax-get-property ACTIVEDOC
        (if (or (eq acmodelspace (vla-get-activespace ACTIVEDOC)) (eq :vlax-true (vla-get-mspace ACTIVEDOC)))
         'modelspace
         'paperspace
        )
       )
 )
 
 (setq ENT (car (entsel "\nSelect first tangent :")))
 (if (/= nil ENT)
  (progn
   (setq ENTLIST (entget ENT))
   (if (= (cdr (assoc 0 ENTLIST)) "LINE")
    (progn
     (command "._LIST" ENT)
     (setq P1 (cdr (assoc 10 ENTLIST)))
     (setq P2 (cdr (assoc 11 ENTLIST)))
     (setq ENT (car (entsel "\nSelect second tangent :")))
     (if (/= nil ENT)
      (progn
       (setq ENTLIST (entget ENT))
       (if (= (cdr (assoc 0 ENTLIST)) "LINE")
        (progn
         (command ENT)
         (setq P3 (cdr (assoc 10 ENTLIST)))
         (setq P4 (cdr (assoc 11 ENTLIST)))
         (setq P (inters P1 P2 P3 P4 nil))
         (if (/= nil P)
          (progn
           (setq VEXAG (getreal (strcat "\nEnter vertical exageration <" (rtos (if RFL:PROFDEFLIST (cdr (assoc "VEXAG" RFL:PROFDEFLIST)) 10.0)) "> :")))
           (if (= VEXAG nil) (setq VEXAG (if RFL:PROFDEFLIST (cdr (assoc "VEXAG" RFL:PROFDEFLIST)) 10.0)))
           (if (/= VEXAG nil)
            (progn
             (if (> VEXAG 0.0)
              (progn
               (if (> (distance P2 P) (distance P1 P))
                (setq P1 P2)
               )
               (if (> (distance P3 P) (distance P4 P))
                (setq P4 P3)
               )
               (setq K nil)
               (setq L nil)
               (setq PP nil)
               (setq G1 (/ (- (nth 1 P) (nth 1 P1))
                           (- (nth 0 P) (nth 0 P1))
                           VEXAG
                        )
               )
               (setq G2 (/ (- (nth 1 P4) (nth 1 P))
                           (- (nth 0 P4) (nth 0 P))
                           VEXAG
                        )
               )
               (while (or (= K nil) (= L nil) (= PP nil))
                (if (= L nil)
                 (progn
                  (setq L (getdist "\nEnter vertical curve 'L' (<return> for 'K') :"))
                  (if (= L nil)
                   (progn
                    (setq L -1.0)
                    (setq K nil)
                    (setq PP -1.0)
                   )
                   (progn
                    (setq K (abs (/ L (- G2 G1) 100.0)))
                    (setq PP -1.0)
                   )
                  )
                 )
                 (progn
                  (if (= K nil)
                   (progn
                    (setq K (getreal "\nEnter vertical curve 'K' (<return> for 'P') :"))
                    (if (= K nil)
                     (progn
                      (setq L -1.0)
                      (setq K -1.0)
                      (setq PP nil)
                     )
                     (progn
                      (setq L (abs (* K (- G2 G1) 100.0)))
                      (setq REP (getreal (strcat "\nL = " (rtos L) ", enter new value or <return> to accept :")))
                      (if (/= nil REP)
                       (progn
                        (setq L REP)
                        (setq K (abs (/ L (- G2 G1) 100.0)))
                       )
                      )
                      (setq PP -1.0)
                     )
                    )
                   )
                   (progn
                    (setq PP (getpoint "\nEnter through point (<return> for 'L') :"))
                    (if (= PP nil)
                     (progn
                      (setq L nil)
                      (setq K -1.0)
                      (setq PP -1.0)
                     )
                     (progn
                      (setq D (- (nth 0 P) (nth 0 PP)))
                      (setq G (- G2 G1))
                      (setq Z (- (/ (nth 1 PP) VEXAG)
                                 (- (/ (nth 1 P) VEXAG)
                                    (* G1 D)
                                 )
                              )
                      )
                      (setq A 0.25)
                      (setq B (* -1.0
                                 (+ D
                                    (/ (* 2.0 Z)
                                       G
                                    )
                                 )
                              )
                      )
                      (setq C (* D D))
                      (setq TMP (- (* B B) (* 4.0 A C)))
                      (if (< TMP 0.0)
                       (progn
                        (princ "\n*** No solution ***")
                        (setq L -1.0)
                        (setq K -1.0)
                        (setq PP nil)
                       )
                       (progn
                        (setq L (/ (- (sqrt TMP) B) (* 2.0 A)))
                        (if (< L 0.0)
                         (progn
                          (princ "\n*** No solution ***")
                          (setq L -1.0)
                          (setq K -1.0)
                          (setq PP nil)
                         )
                         (progn
                          (setq REP (getreal (strcat "\nL = " (rtos L) ", enter new value or <return> to accept :")))
                          (if (/= nil REP)
                           (progn
                            (setq L REP)
                           )
                          )
                          (setq K (abs (/ L (- G2 G1) 100.0)))
                         )
                        )
                       )
                      )
                     )
                    )
                   )
                  )
                 )
                )
               )
               (command)
               (setvar "OSMODE" 0)
               (setvar "ATTREQ" 0)
               (if (= nil (tblsearch "BLOCK" "PVI2")) (RFL:MAKEENT "PVI2"))
               (vla-insertblock ACTIVESPC
                                (vlax-3D-point P)
                                "PVI2"
                                25.4
                                25.4
                                25.4
                                0.0
               )
               (setq ENT (entlast))
               (setq ENTLIST (entget ENT))
               (if (= (cdr (assoc 66 ENTLIST)) 1)
                (progn
                 (setq ENT (entnext ENT))
                 (setq ENTLIST (entget ENT))
                 (while (/= (cdr (assoc 0 ENTLIST)) "SEQEND")
                  (if (= (cdr (assoc 2 ENTLIST)) "LENGTH")
                   (progn
                    (setq ENTLIST (subst (cons 1 (rtos L 2 8)) (assoc 1 ENTLIST) ENTLIST))
                    (entmod ENTLIST)
                    (entupd ENT)
                   )
                  )
                  (if (= (cdr (assoc 2 ENTLIST)) "K")
                   (progn
                    (setq ENTLIST (subst (cons 1 (rtos K 2 8)) (assoc 1 ENTLIST) ENTLIST))
                    (entmod ENTLIST)
                    (entupd ENT)
                   )
                  )
                  (setq ENT (entnext ENT))
                  (setq ENTLIST (entget ENT))
                 )
                )
               )
               (setvar "ATTREQ" 1)
               (setq P2 (list (- (nth 0 P) (/ L 2.0))
                              (- (nth 1 P) (* (/ L 2.0) G1 VEXAG))
                        )
               )
               (setq P3 (list (+ (nth 0 P) (/ L 2.0))
                              (+ (nth 1 P) (* (/ L 2.0) G2 VEXAG))
                        )
               )
               (RFL:DRAWPARABOLICVCURVE P2 P P3)
               (setvar "OSMODE" OSMODE)
              )
              (princ "\n**** NOT VALID ****")
             )
            )
           )
          )
          (princ "\n**** NO INTERSECTION FOUND ****")
         )
        )
        (princ "\n**** NOT A LINE ****")
       )
      )
     )
    )
    (princ "\n**** NOT A LINE ****")
   )
  )
 )
)
