;
;
;     Program written by Robert Livingston, 2015-02-20
;
;     C:PGRADE is a routine for finding a polyline with constant grade along a surface between two selected points
;
;
(defun C:PGRADE (/ *error* ANG ANGBASE ANGDIR CMDECHO CONTINUE D DIST2D GETOS GRADE GRSECTION NODE OBSURFACE OGLIST OS OSMODE P P0 P1 P2 PL PR REP STEP SWATH TMP Z0 Z1 Z2)
;(defun C:PGRADE ()
 (command "._UNDO" "M")
 (command "._UCS" "W")
 (setq CMDECHO (getvar "CMDECHO"))
 (setvar "CMDECHO" 0)
 (setq OSMODE (getvar "OSMODE"))
 (setq ANGBASE (getvar "ANGBASE"))
 (setvar "ANGBASE" 0.0)
 (setq ANGDIR (getvar "ANGDIR"))
 (setvar "ANGDIR" 0)
 (setq ALSAVE RFL:ALIGNLIST)

 (defun *error* (msg)
  (if (>= (atof (getvar "ACADVER")) 18.2)
   (command-s "._UCS" "P")
   (command "._UCS" "P")
  )
  (setvar "CMDECHO" CMDECHO)
  (setvar "ANGBASE" ANGBASE)
  (setvar "ANGDIR" ANGDIR)
  (setvar "OSMODE" OSMODE)
  (setq RFL:ALIGNLIST ALSAVE)
  ;(setq *error* nil)
  (print msg)
 )

 (defun GETOS (/ C OSBEST L P1 P2 P3 P4 TMP ZBEST)
  (setq OSBEST nil ZBEST nil)
  (setq C 0)
  (while (< (+ C 1) (length OGLIST))
   (setq P1 (nth C OGLIST))
   (setq L (sqrt (+ (expt (car P1) 2) (expt D 2))))
   (setq P3 (list (car P1) (+ Z0 (* L GRADE))))
   (setq P2 (nth (+ C 1) OGLIST))
   (setq L (sqrt (+ (expt (car P2) 2) (expt D 2))))
   (setq P4 (list (car P2) (+ Z0 (* L GRADE))))
   (setq TMP (inters P1 P2 P3 P4))
   (if (/= nil TMP)
    (if (= nil OSBEST)
     (setq OSBEST (car TMP) ZBEST (cadr TMP))
     (if (< (abs (car TMP)) (abs OSBEST))
      (setq OSBEST (car TMP) ZBEST (cadr TMP))
     )
    )
   )
   (setq C (+ C 1))
  )
  (list OSBEST ZBEST)
 )
 
 (defun GRSECTION (/ C H NODE P1 P2 PC PB SCALE)
  (setq PC (getvar "VIEWCTR"))
  (setq H (getvar "VIEWSIZE"))
  (setq PB (list (+ (car PC) (/ H 3.0)) (- (cadr PC) (/ H 4.0))))
  (setq SCALE (/ (/ H 2.0) SWATH))
  (setq C 0)
  (setq P1 (nth C OGLIST))
  (setq P1 (list (+ (car PB) (* SCALE (car P1))) (+ (cadr PB) (* SCALE (- (cadr P1) Z2)))))
  (while (< (+ C 1) (length OGLIST))
   (progn
    (setq P2 (nth (+ C 1) OGLIST))
    (setq P2 (list (+ (car PB) (* SCALE (car P2))) (+ (cadr PB) (* SCALE (- (cadr P2) Z2)))))
    (grdraw P1 P2 -1)
    (setq P1 P2)
    (setq C (+ C 1))
   )
  )
  (setq P1 (list (+ (car PB) (* SCALE (car OS))) (+ (cadr PB) (* SCALE (- (cadr OS) Z2)))))
  (grdraw (list (+ (car P1) (/ H -25.0)) (cadr P1))
          (list (+ (car P1) (/ H 25.0)) (cadr P1)) -1)
  (grdraw (list (car P1) (+ (cadr P1) (/ H -25.0)))
          (list (car P1) (+ (cadr P1) (/ H 25.0))) -1)
 )
 
 (defun DIST2D (P1 P2)
  (distance (list (car P1) (cadr P1)) (list (car P2) (cadr P2)))
 )
 
 (if (/= nil (setq OBSURFACE (RFL:GETC3DSURFACE)))
  (if (/= nil (setq P0 (getpoint "\nStart Point : ")))
   (if (/= nil (setq Z0 (RFL:GETSURFACEPOINT P0 OBSURFACE)))
    (progn
     (setq P0 (list (car P0) (cadr P0)))
     (princ (strcat "\nElevation at start point = " (rtos Z0)))
     (setq P2 (getpoint "\nPick second point for grade reference : "))
     (if (/= nil (setq Z2 (RFL:GETSURFACEPOINT P2 OBSURFACE)))
      (progn
       (setq GRADE (* 100.0 (/ (- Z2 Z0) (DIST2D P0 P2))))
       (setq REP (getreal (strcat "\nEnter desired grade (%) <" (rtos GRADE) "> : ")))
       (if (/= nil REP) (setq GRADE REP))
       (setq GRADE (/ GRADE 100.0))
       (setq SWATH 500.0)
       (setq REP (getreal (strcat "\nEnter swath width <" (rtos SWATH) "> : ")))
       (if (/= nil REP) (setq SWATH REP))
       ;(setq STEP 100.0)
       ;(setq REP (getreal (strcat "\nEnter step size <" (rtos STEP) "> : ")))
       ;(if (/= nil REP) (setq STEP REP))
        (setq CONTINUE T)
       (setvar "OSMODE" 0)
       (command "._PLINE" P0)
       (princ (strcat "\n" (rtos (* GRADE 100.0)) "%, Point : "))
       (while (and (or (= 5 (car (setq P1 (grread T))))
                       (= 3 (car P1))
                       (= 2 (car P1))
                   )
                   CONTINUE
              )
        (if (= 2 (car P1))
         (if (= 43 (cadr P1))
          (progn
           (setq GRADE (+ GRADE 0.001))
           (princ (strcat "\n" (rtos (* GRADE 100.0)) "%, Point : "))
          )
          (if (= 45 (cadr P1))
           (progn
            (setq GRADE (- GRADE 0.001))
            (princ (strcat "\n" (rtos (* GRADE 100.0)) "%, Point : "))
           )
           (if (= 13 (cadr P1))
            (setq CONTINUE nil)
            (if (= 32 (cadr P1))
             (setq CONTINUE nil)
            )
           )
          )
         )
         (progn
          (setq P (list (caadr P1) (cadadr P1)))
          (setq ANG (angle P0 P))
          (setq D (DIST2D P0 P))
          (setq P2 nil)
          (setq RFL:ALIGNLIST (list (list 0.0 P0 (list (+ (car P0) (* 2.0 D (cos ANG))) (+ (cadr P0) (* 2.0 D (sin ANG)))) 0.0)))
          (setq PL (RFL:XY (list D (/ SWATH -2.0))))
          (setq PR (RFL:XY (list D (/ SWATH 2.0))))
          (setq OGLIST nil)
          (if (and (/= nil PL) (/= nil PR))
           (progn
            (setq TMP (RFL:GETSURFACELINE PL P OBSURFACE))
            (foreach NODE TMP
             (setq OGLIST (append OGLIST (list (list (* -1.0 (DIST2D NODE P)) (last NODE)))))
            )
            (setq TMP (cdr (RFL:GETSURFACELINE P PR OBSURFACE)))
            (foreach NODE TMP
             (setq OGLIST (append OGLIST (list (list (DIST2D NODE P) (last NODE)))))
            )
           )
          )
          (if (/= nil OGLIST)
           (if (/= nil (car (setq OS (GETOS))))
            (progn
             (command "'REDRAW")
             (if (and (/= nil PL) (/= nil PR)) (grdraw PL PR -1))
             (GRSECTION)
             (setq P2 (RFL:XY (list D (car OS))))
             (setq Z2 (cadr OS))
             (grdraw P0 P2 -1)
            )
           )
          )
          (if (= 3 (car P1))
           (if (/= nil P2)
            (progn
             (command "'REDRAW")
             (setq P0 P2 Z0 Z2)
             (command P0)
             (princ (strcat "\n" (rtos (* GRADE 100.0)) "%, Point : "))
            )
           )
          )
         )
        )
       )
       (command "")
      )
     )
    )
   )
  )
 )

 (command "._UCS" "P")
 (setvar "CMDECHO" CMDECHO)
 (setvar "ANGBASE" ANGBASE)
 (setvar "ANGDIR" ANGDIR)
 (setvar "OSMODE" OSMODE)
 (setq RFL:ALIGNLIST ALSAVE)
 (command "'REDRAW")
 nil
)
