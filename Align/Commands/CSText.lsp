;
;
;     Program written by Robert Livingston, 2001/01/02
;
;     STEXT is a utility for "sliding" text along it's axis
;
;
(defun C:STEXT (/ *error* CMDECHO ENT ENTLIST ORTHOMODE SNAPANG)
 (setq CMDECHO (getvar "CMDECHO"))
 (setvar "CMDECHO" 1)
 (setq ORTHOMODE (getvar "ORTHOMODE"))
 (setvar "ORTHOMODE" 1)
 (setq SNAPANG (getvar "SNAPANG"))

 (defun *error* (msg)
  (if (>= (atof (getvar "ACADVER")) 18.2)
   (command-s "._UCS" "P")
   (command "._UCS" "P")
  )
  (setvar "CMDECHO" CMDECHO)
  (setvar "ORTHOMODE" ORTHOMODE)
  (setvar "SNAPANG" SNAPANG)
  (princ msg)
  ;(setq *error* nil)
 )

 (command "._UCS" "W")

 (setq ENT (car (entsel "\nSelect text :")))
 (if (/= nil ENT)
  (progn
   (setq ENTLIST (entget ENT))
   (if (or (= (cdr (assoc 0 ENTLIST)) "TEXT") (= (cdr (assoc 0 ENTLIST)) "MTEXT"))
    (progn
     (setq P nil)
     (if (and (= (cdr (assoc 0 ENTLIST)) "TEXT")
              (or (/= (cdr (assoc 72 ENTLIST)) 0)
                  (/= (cdr (assoc 73 ENTLIST)) 0)
              )
         )
      (setq P (cdr (assoc 11 ENTLIST)))
     )
     (if (= nil P)
      (setq P (cdr (assoc 10 ENTLIST)))
     )
     (setvar "SNAPANG" (cdr (assoc 50 ENTLIST)))
     (command "._MOVE" ENT "" "_NON" P "_NON" "\\")
    )
   )
  )
 )

 (command "._UCS" "P")
 (setvar "CMDECHO" CMDECHO)
 (setvar "ORTHOMODE" ORTHOMODE)
 (setvar "SNAPANG" SNAPANG)
)
(defun C:STEXTM (/ *error* CMDECHO ENT ENTLIST ENTSET ORTHOMODE SNAPANG)
 (setq CMDECHO (getvar "CMDECHO"))
 (setvar "CMDECHO" 1)
 (setq ORTHOMODE (getvar "ORTHOMODE"))
 (setvar "ORTHOMODE" 1)
 (setq SNAPANG (getvar "SNAPANG"))

 (defun *error* (msg)
  (command "._UCS" "P")
  (setvar "CMDECHO" CMDECHO)
  (setvar "ORTHOMODE" ORTHOMODE)
  (setvar "SNAPANG" SNAPANG)
  (princ msg)
  ;(setq *error* nil)
 )

 (command "._UCS" "W")

 (setq ENT (car (entsel "\nSelect text :")))
 (if (/= nil ENT)
  (progn
   (setq ENTLIST (entget ENT))
   (if (or (= (cdr (assoc 0 ENTLIST)) "TEXT") (= (cdr (assoc 0 ENTLIST)) "MTEXT"))
    (progn
     (setq P nil)
     (if (and (= (cdr (assoc 0 ENTLIST)) "TEXT")
              (or (/= (cdr (assoc 72 ENTLIST)) 0)
                  (/= (cdr (assoc 73 ENTLIST)) 0)
              )
         )
      (setq P (cdr (assoc 11 ENTLIST)))
     )
     (if (= nil P)
      (setq P (cdr (assoc 10 ENTLIST)))
     )
     (setvar "SNAPANG" (cdr (assoc 50 ENTLIST)))
     (setq ENTSET (ssadd ENT))
     (while (/= (setq ENT (car (entsel "\nSelect entity :"))) nil)
      (ssadd ENT ENTSET)
     )
     (command "._MOVE" ENTSET "" "_NON" P "_NON" "\\")
    )
   )
  )
 )

 (command "._UCS" "P")
 (setvar "CMDECHO" CMDECHO)
 (setvar "ORTHOMODE" ORTHOMODE)
 (setvar "SNAPANG" SNAPANG)
)
