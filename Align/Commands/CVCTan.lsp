;
;
;     Program written by Robert Livingston, 0/12/18
;
;     VCTAN returns the tangent from a point to a vertical curve
;
(defun C:VCTAN (/ A B C ENT ENTLIST G1 G2 P P1 P2 P3 PE RFL:PVILIST SA SB SC X X0A X0B X1 X2 X3 Y Y0A Y0B Y1 Y2 Y3 TMP)
 (setq P (getvar "LASTPOINT"))
 (setq X (nth 0 P))
 (setq Y (nth 1 P))
 (setq ENT (entsel "\nSelect vertical curve :"))
 (setq PE (cadr ENT))
 (setq ENT (car ENT))
 (if (and (/= nil ENT) (/= nil P))
  (progn
   (setq P1 nil P2 nil P3 nil)
   (setq ENTLIST (entget ENT))
   (if (= "POLYLINE" (cdr (assoc 0 ENTLIST)))
    (progn
     (setq ENT (entnext ENT))
     (setq ENTLIST (entget ENT))
     (setq P1 (cdr (assoc 10 ENTLIST)))
     (setq ENT (entnext ENT))
     (setq ENTLIST (entget ENT))
     (setq P2 (cdr (assoc 10 ENTLIST)))
     (if (/= nil P2)
      (progn
       (setq ENT (entnext ENT))
       (setq ENTLIST (entget ENT))
       (setq P3 (cdr (assoc 10 ENTLIST)))
       (if (/= nil P3)
        (progn
         (setq ENT (entnext ENT))
         (setq ENTLIST (entget ENT))
         (while (/= "SEQEND" (cdr (assoc 0 ENTLIST)))
          (setq P2 P3)
          (setq P3 (cdr (assoc 10 ENTLIST)))
          (setq ENT (entnext ENT))
          (setq ENTLIST (entget ENT))
         )
        )
       )
      )
     )
    )
   )
   (if (= "AECC_PROFILE" (cdr (assoc 0 ENTLIST)))
    (progn
     (setq RFL:PVILIST nil)
     (RFL:RPROFC3D ENT)
     (if (/= RFL:PVILIST nil)
      (progn
       (setq C 0)
       (while (< C (length RFL:PVILIST))
        
        
        (setq C (1+ C))
       )
      )
     )
    )
   )
   (if (and (/= nil P1) (/= nil P2) (/= nil P3))
    (progn
     (setq X1 (nth 0 P1))
     (setq Y1 (nth 1 P1))
     (setq X2 (nth 0 P2))
     (setq Y2 (nth 1 P2))
     (setq X3 (nth 0 P3))
     (setq Y3 (nth 1 P3))
     (setq G1 (/ (- Y2 Y1) (- X2 X1)))
     (setq G2 (/ (- Y3 Y2) (- X3 X2)))
     (setq A (/ (- G2 G1) (- X3 X1) 2.0))
     (setq B (/ (- G2 (* G1 (/ X3 X1))) (- 1.0 (/ X3 X1))))
     (setq C (- Y1 (+ (* A X1 X1) (* B X1))))
     (setq SA A)
     (setq SB (* -2.0 A X))
     (setq SC (- Y C (* B X)))
     (setq X0A (/ (+ (* -1.0 SB) (sqrt (- (* SB SB) (* 4.0 SA SC)))) (* 2.0 SA)))
     (setq Y0A (+ (* A X0A X0A) (* B X0A) C))
     (setq X0B (/ (- (* -1.0 SB) (sqrt (- (* SB SB) (* 4.0 SA SC)))) (* 2.0 SA)))
     (setq Y0B (+ (* A X0B X0B) (* B X0B) C))
     (if (> X0A X0B)
      (progn
       (setq TMP X0A)
       (setq X0A X0B)
       (setq X0B TMP)
       (setq TMP Y0A)
       (setq Y0A Y0B)
       (setq Y0B TMP)
      )
     )
     (princ "\nPick side :")
     (while (= (car (setq TMP (grread nil 1))) 5)
     )
     (if (= (car TMP) 3)
      (if (< (nth 0 (car (cdr TMP))) X)
       (list X0A Y0A)
       (list X0B Y0B)
      )
      nil
     )
    )
    nil
   )
  )
 )
)
