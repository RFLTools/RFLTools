;
;
;     Program written by Robert Livingston, 2015-08-19
;
;     C:3DP2MINPROF generates a profile by projecting selected 3DPolyline points to the proposed alignment
;
;
(defun C:3DP2MINPROF (/ *error* ALINTERS ALPLALPLLIST ALSAVE C ENT ENTLIST INC NODE ORTHOMODE OS OSMODE P P1 P2 PLIST PVIPL PVIPLLIST PVISAVE S STA STAEND SWATH TMP Z Z1 Z2 ZLIST ZMAX)
 (setq OSMODE (getvar "OSMODE"))
 (setvar "OSMODE" 0)
 (setq ORTHOMODE (getvar "ORTHOMODE"))
 (setvar "ORTHOMODE" 0)
 
 (defun *error* (msg)
  (setq RFL:ALIGNLIST ALSAVE)
  (setq PVISAVE RFL:PVILIST)
  (setvar "OSMODE" OSMODE)
  (setvar "ORTHOMODE" ORTHOMODE)
  (print msg)
  ;(setq *error* nil)
 )
 
 (defun ALINTERS (P1 P2 RFL:ALIGNLIST / C OS OS1 OS2 P)
  (setq P nil)
  (while (and (/= nil RFL:ALIGNLIST)
              (= nil (setq P (inters P1 P2 (cadr (car RFL:ALIGNLIST)) (caddr (car RFL:ALIGNLIST)))))
         )
   (setq RFL:ALIGNLIST (cdr RFL:ALIGNLIST))
  )
  P
 )
 
 (setq ALSAVE RFL:ALIGNLIST)
 (setq PVISAVE RFL:PVILIST)
 (if (= nil RFL:ALIGNLIST)
  (princ "\n!!! NO ALIGNMENT DEFINED !!!\n")
  (progn
   (setq INC 0.0)
   (while (= INC 0.0)
    (setq INC (getdist "\nStation increment <10.0> : "))
    (if (= INC nil) (setq INC 10.0))
   )
   (setq TMP (+ INC (* INC (fix (/ (caar RFL:ALIGNLIST) INC)))))
   (setq STA (getreal (strcat "\nStart Station <" (rtos TMP 2 3) "> : ")))
   (if (= nil STA) (setq STA TMP))
   (setq TMP (* INC (fix (/ (+ (caar RFL:ALIGNLIST) (RFL:GETALIGNLENGTH)) INC))))
   (setq STAEND (getreal (strcat "\nEnd Station <" (rtos TMP 2 3) "> : ")))
   (if (= nil STAEND) (setq STAEND TMP))
   (setq ALPLLIST nil)
   (setq PVIPLLIST nil)
   (RFL:PROFDEF)
   (while (/= nil (setq ENT (car (entsel "\nSelect Polyline : "))))
    (setq ENTLIST (entget ENT))
    (if (= (cdr (assoc 0 ENTLIST)) "POLYLINE")
     (if (/= 0 (logand (cdr (assoc 70 ENTLIST)) 8))
      (progn
       (setq ALPL nil)
       (setq PVIPL nil)
       (setq ENT (entnext ENT))
       (setq ENTLIST (entget ENT))
       (setq P1 nil)
       (setq Z1 nil)
       (while (/= (cdr (assoc 0 ENTLIST)) "SEQEND")
        (setq P2 (cdr (assoc 10 ENTLIST)))
        (setq Z2 (caddr P2))
        (if (= Z2 nil) (setq Z2 0.0))
        (setq P2 (list (car P2) (cadr P2)))
        (if (/= P1 nil)
         (if (= nil ALPL)
          (setq ALPL (list (list 0.0 P1 P2 0.0)))
          (setq ALPL (append ALPL (list (list (+ (car (last ALPL)) (distance (cadr (last ALPL)) (caddr (last ALPL)))) P1 P2 0.0))))
         )
        )
        (if (= nil PVIPL)
         (setq PVIPL (list (list 0.0 Z2 "L" 0.0)))
         (setq PVIPL (append PVIPL (list (list (+ (car (last ALPL)) (distance P1 P2)) Z2 "L" 0.0))))
        )
        (setq P1 P2)
        (setq ENT (entnext ENT))
        (setq ENTLIST (entget ENT))
       )
       (setq ALPLLIST (append ALPLLIST (list ALPL)))
       (setq PVIPLLIST (append PVIPLLIST (list PVIPL)))
      )
      (princ "\n!!! NOT a 3D POLYLINE !!!\n")
     )
    )
   )
   (if (/= nil ALPLLIST)
    (progn
     (command "._PLINE")
     (setq SWATH (getdist "\nSwath with <100.0> : "))
     (if (= nil SWATH) (setq SWATH 100.0))
     (while (<= STA STAEND)
      (setq RFL:ALIGNLIST ALSAVE)
      (setq P1 (RFL:XY (list STA (/ SWATH -2.0))))
      (setq P2 (RFL:XY (list STA (/ SWATH 2.0))))
      (setq PLIST nil)
      (setq ZLIST nil)
      (setq C 0)
      (while (< C (length ALPLLIST))
       (setq RFL:ALIGNLIST (nth C ALPLLIST))
       (setq RFL:PVILIST (nth C PVIPLLIST))
       (setq P (ALINTERS P1 P2 RFL:ALIGNLIST))
       (if (/= nil P)
        (progn
         (setq Z (RFL:ELEVATION (car (RFL:STAOFF P))))
         (if (/= nil Z)
          (progn
           (setq PLIST (append PLIST (list P)))
           (setq ZLIST (append ZLIST (list Z)))
          )
         )
        )
       )
       (setq C (+ C 1))
      )
      (setq RFL:ALIGNLIST ALSAVE)
      (if (and (/= nil PLIST) (/= nil ZLIST))
       (progn
        (setq ZMAX nil)
        (if (/= nil (setq P (RFL:XY (list STA 0.0))))
         (if (/= nil (setq S (RFL:SUPER STA)))
          (progn
           (setq C 0)
           (while (< C (length PLIST))
            (setq P1 (nth C PLIST))
            (setq Z1 (nth C ZLIST))
            (if (/= nil (setq OS (cadr (RFL:STAOFF P1))))
             (progn
              (if (< OS 0.0)
               (setq Z (+ Z1 (* (abs OS) (car S) -0.01)))
               (setq Z (+ Z1 (* (abs OS) (cadr S) -0.01)))
              )
              (if (= ZMAX nil)
               (setq ZMAX Z)
               (if (> Z ZMAX)
                (setq ZMAX Z)
               )
              )
             )
            )
            (setq C (+ C 1))
           )
           (if (/= nil ZMAX)
            (command (RFL:PROFPOINT STA ZMAX))
           )
          )
         )
        )
       )
      )
      (princ (strcat "\nSta : " (RFL:STATXT STA)))
      (setq STA (+ STA INC))
     )
     (command "")
    )
   )
  )
 )
 (setq RFL:ALIGNLIST ALSAVE)
 (setq PVISAVE RFL:PVILIST)
 (setvar "OSMODE" OSMODE)
 (setvar "ORTHOMODE" ORTHOMODE)
 T
)
