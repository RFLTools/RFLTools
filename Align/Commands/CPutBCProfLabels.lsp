;
;
;     Program written by Robert Livingston, 2022-01-31
;
;     C:PUTBCPROFLABELS created and inserts profile label blocks along the top of selected profile views
;
;
;          Thanks to Lee Mac for RTOC
(defun RFL:RTOC ( n p / d i l x )
    (setq d (getvar 'dimzin))
    (setvar 'dimzin 0)
    (setq l (vl-string->list (rtos (abs n) 2 p))
          x (cond ((cdr (member 46 (reverse l)))) ((reverse l)))
          i 0
    )
    (setvar 'dimzin d)
    (vl-list->string
        (append (if (minusp n) '(45))
            (reverse
                (apply 'append
                    (mapcar
                       '(lambda ( a b )
                            (if (and (zerop (rem (setq i (1+ i)) 3)) b)
                                (list a 44)
                                (list a)
                            )
                        )
                        x (append (cdr x) '(nil))
                    )
                )
            )
            (member 46 l)
        )
    )
)
(setq RFL:PROFLABELH 7.0)
(setq RFL:PROFLABELS 16.0)
(setq RFL:PROFLABELB "RFLPROFVOLNODE")
(defun C:PUTBCPROFLABELS (/ AREA AREALIST C C1 C2 ENT ENTLIST ENTOB ENTSET ENTSETVOLUME FLAG GETAREALIST INFILENAME MATERIALLIST MIDP P P1 P2 PV1 PV2 SECTIONLIST SECTIONLIST2 S1 S2 STA1 STA2 TMP TXT VOLUME VOLUMELIST X X1 X2 XSTART XEND Y)
 (command "._UNDO" "M")
 (defun MIDP (P1 P2)
  (if (and (caddr P1) (caddr P2))
   (list (/ (+ (car P1) (car P2)) 2.0) (/ (+ (cadr P1) (cadr P2)) 2.0) (/ (+ (caddr P1) (caddr P2)) 2.0))
   (list (/ (+ (car P1) (car P2)) 2.0) (/ (+ (cadr P1) (cadr P2)) 2.0) 0.0)
  )
 )
 (defun GETAREALIST (STA1 STA2 AREA1 AREA2 SECTIONLIST TXT / AREALIST)
  (while (and SECTIONLIST (> STA1 (cadr (car SECTIONLIST)))) (setq SECTIONLIST (cdr SECTIONLIST)))
  (setq SECTIONLIST (reverse SECTIONLIST))
  (while (and SECTIONLIST (< STA2 (cadr (car SECTIONLIST)))) (setq SECTIONLIST (cdr SECTIONLIST)))
  (setq SECTIONLIST (reverse SECTIONLIST))
  (cond ((= (strcase TXT) "CUT")
         (progn
          (if AREA1 (setq AREALIST (list (list STA1 (car AREA1)))))
          (while (and SECTIONLIST (> STA2 (cadr (car SECTIONLIST))))
           (setq AREALIST (append AREALIST (list (list (cadr (car SECTIONLIST)) (caddr (car SECTIONLIST))))))
           (setq SECTIONLIST (cdr SECTIONLIST))
          )
          (if AREA2 (setq AREALIST (append AREALIST (list (list STA2 (car AREA2))))))
         )
        )
        ((= (strcase TXT) "FILL")
         (progn
          (if AREA1 (setq AREALIST (list (list STA1 (cadr AREA1)))))
          (while (and SECTIONLIST (> STA2 (cadr (car SECTIONLIST))))
           (setq AREALIST (append AREALIST (list (list (cadr (car SECTIONLIST)) (cadddr (car SECTIONLIST))))))
           (setq SECTIONLIST (cdr SECTIONLIST))
          )
          (if AREA2 (setq AREALIST (append AREALIST (list (list STA2 (cadr AREA2))))))
         )
        )
        (T
         (progn
          (if AREA1 (setq AREALIST (list (list STA1 (RFL:GETMATAREA TXT (last AREA1))))))
          (while (and SECTIONLIST (> STA2 (cadr (car SECTIONLIST))))
           (setq AREALIST (append AREALIST (list (list (cadr (car SECTIONLIST)) (RFL:GETMATAREA TXT (last (car SECTIONLIST)))))))
           (setq SECTIONLIST (cdr SECTIONLIST))
          )
          (if AREA2 (setq AREALIST (append AREALIST (list (list STA2 (RFL:GETMATAREA TXT (last AREA2)))))))
         )
        )
  )
  AREALIST
 )
 (if (setq INFILENAME (getfiled "Select XML file for input" "" "xml" 2))
  (if (setq SECTIONLIST (RFL:GETSECTIONSXML INFILENAME))
   (if (setq MATERIALLIST (RFL:GETMATERIALSXML INFILENAME))
    (progn
     (setq MATERIALLIST (append (list "CUT" "FILL") MATERIALLIST))
     (princ "\nSelect profile views.")
     (if (setq ENTSET (ssget))
      (progn
       (if (= nil (tblsearch "BLOCK" RFL:PROFLABELB)) (RFL:MAKEENT RFL:PROFLABELB))
       (if (tblsearch "BLOCK" RFL:PROFLABELB)
        (progn
         (setq C 0)
         (while (< C (sslength ENTSET))
          (setq ENT (ssname ENTSET C))
          (setq ENTLIST (entget ENT))
          (if (= (cdr (assoc 0 ENTLIST)) "AECC_PROFILE_VIEW")
           (progn
            (setq ENTOB (vlax-ename->vla-object ENT))
            (vlax-invoke-method ENTOB 'getboundingbox 'PV1 'PV2)
            (setq PV1 (vlax-safearray->list PV1))
            (setq PV2 (vlax-safearray->list PV2))
            (setq STA1 (vlax-get-property ENTOB 'StationStart))
            (setq STA2 (vlax-get-property ENTOB 'StationEnd))
            (vlax-invoke-method ENTOB 'FindXYAtStationAndElevation STA1 0.0 'XSTART 'Y)
            (vlax-invoke-method ENTOB 'FindXYAtStationAndElevation STA2 0.0 'XEND 'Y)
            (setq P1 (list XSTART (cadr PV2) 0.0))
            (setq P2 (list XEND (cadr PV2) 0.0))
            (setq ENTSETVOLUME (ssadd))
            (setq AREA1 (RFL:GETAREA SECTIONLIST STA1))
            (setq AREA2 (RFL:GETAREA SECTIONLIST STA2))
            (foreach TXT (reverse MATERIALLIST)
             (RFL:ADDTEXT P1 "MR" RFL:PROFLABELH TXT)
             (setq AREALIST (GETAREALIST STA1 STA2 AREA1 AREA2 SECTIONLIST TXT))
             (cond ((and AREA1 AREA2) ; No NILL
                    (progn
                     (if (and (= (cadr (car AREALIST)) 0.0) (= (cadr (cadr AREALIST)) 0.0))
                      (setq FLAG T)
                      (setq FLAG nil)
                     )
                     (while AREALIST
                      (if FLAG
                       (progn
                        (setq S1 (caar AREALIST))
                        (setq S2 S1)
                        (setq AREALIST (cdr AREALIST))
                        (while (and AREALIST (= (cadr (car AREALIST)) 0.0))
                         (setq S2 (car (car AREALIST)))
                         (setq AREALIST (cdr AREALIST))
                        )
                        (vlax-invoke-method ENTOB 'FindXYAtStationAndElevation S1 0.0 'X1 'Y)
                        (vlax-invoke-method ENTOB 'FindXYAtStationAndElevation S2 0.0 'X2 'Y)
                        (entmake (list (cons 0 "LINE")
                                       (list 10 X1 (- (cadr P1) (/ RFL:PROFLABELS 2.0)) 0.0)
                                       (list 11 X1 (+ (cadr P1) (/ RFL:PROFLABELS 2.0)) 0.0)
                                 )
                        )
                        (entmake (list (cons 0 "LINE")
                                       (list 10 X2 (- (cadr P1) (/ RFL:PROFLABELS 2.0)) 0.0)
                                       (list 11 X2 (+ (cadr P1) (/ RFL:PROFLABELS 2.0)) 0.0)
                                 )
                        )
                        (RFL:ADDTEXT (list (/ (+ X1 X2) 2.0) (cadr P1) 0.0) "M" RFL:PROFLABELH "NIL")
                        (setq FLAG nil)
                       )
                       (progn
                        (setq S1 (caar AREALIST))
                        (setq S2 S1)
                        (setq AREALIST (cdr AREALIST))
                        (while (and AREALIST (or (/= (cadr (car AREALIST)) 0.0) (/= (cadr (cadr AREALIST)) 0.0)))
                         (setq S2 (caar AREALIST))
                         (setq AREALIST (cdr AREALIST))
                        )
                        (vlax-invoke-method ENTOB 'FindXYAtStationAndElevation S1 0.0 'X1 'Y)
                        (vlax-invoke-method ENTOB 'FindXYAtStationAndElevation S2 0.0 'X2 'Y)
                        (setq TMP (RFL:GETMATVOLUME TXT SECTIONLIST S1 S2))
                        (if TMP
                         (setq TMP (RFL:RTOC TMP 0))
                         (setq TMP "?")
                        )
                        (RFL:ADDTEXT (list (/ (+ X1 X2) 2.0) (cadr P1) 0.0) "M" RFL:PROFLABELH TMP)
                        (setq FLAG T)
                       )
                      )
                     )
                    )
                   )
                   (AREA1             ; Add NILL at end
                    (progn
                     (setq STA2 (cadr (last SECTIONLIST)))
                     (vlax-invoke-method ENTOB 'FindXYAtStationAndElevation STA2 0.0 'X 'Y)
                     (entmake (list (cons 0 "LINE")
                                    (list 10 X (- (cadr P1) (/ RFL:PROFLABELS 2.0)) 0.0)
                                    (list 11 X (+ (cadr P1) (/ RFL:PROFLABELS 2.0)) 0.0)
                              )
                     )
                     (RFL:ADDTEXT (list (/ (+ X (car P2)) 2.0) (cadr P2) 0.0) "M" RFL:PROFLABELH "NIL")
                     (setq P (list X (cadr P1) 0.0))
                     (setq TMP (RFL:GETMATVOLUME TXT SECTIONLIST STA1 STA2))
                     (if TMP
                      (setq TMP (RFL:RTOC TMP 0))
                      (setq TMP "?")
                     )
                     (RFL:ADDTEXT (MIDP P1 P) "M" RFL:PROFLABELH TMP)
                    )
                   )
                   (AREA2             ; Add NILL at begining
                    (progn
                     (setq STA1 (cadr (car SECTIONLIST)))
                     (vlax-invoke-method ENTOB 'FindXYAtStationAndElevation STA1 0.0 'X 'Y)
                     (entmake (list (cons 0 "LINE")
                                    (list 10 X (- (cadr P1) (/ RFL:PROFLABELS 2.0)) 0.0)
                                    (list 11 X (+ (cadr P1) (/ RFL:PROFLABELS 2.0)) 0.0)
                              )
                     )
                     (RFL:ADDTEXT (list (/ (+ X (car P1)) 2.0) (cadr P1) 0.0) "M" RFL:PROFLABELH "NIL")
                     (setq P (list X (cadr P1) 0.0))
                     (setq TMP (RFL:GETMATVOLUME TXT SECTIONLIST STA1 STA2))
                     (if TMP
                      (setq TMP (RFL:RTOC TMP 0))
                      (setq TMP "?")
                     )
                     (RFL:ADDTEXT (MIDP P P2) "M" RFL:PROFLABELH TMP)
                    )
                   )
                   (T                 ; Add NILL full
                    (progn
                     (RFL:ADDTEXT (list (/ (+ (car P1) (car P2)) 2.0) (cadr P1) 0.0) "M" RFL:PROFLABELH "NIL")
                    )
                   )
             )
             (setq P1 (list (car P1) (+ (cadr P1) RFL:PROFLABELS) 0.0))
             (setq P2 (list (car P2) (+ (cadr P2) RFL:PROFLABELS) 0.0))
            )
;            (RFL:UPDATEXMLVOLUME ENTSETVOLUME)
           )
          )
          (setq C (1+ C))
         )
        )
        (princ "\nUnable to create text node block!")
       )
      )
     )
    )
    (princ "\nUnable to retrieve material list from XML file!")
   )
   (princ "\nUnable to retreive sections from XML!")
  )
 )
 nil
)
