;
;
;     Program written by Robert Livingston, 2015-02-20
;
;     C:PCHANNEL is a routine for finding a simple flat bottom section with constant grade along a surface between two selected points
;
;
(defun C:PCHANNEL (/ *error* ANG ANGBASE ANGDIR CMDECHO CONTINUE CSLOPE CWIDTH2 D D1 D2 DIST2D ENT ENTOBJ ENTL ENTLOBJ ENTR ENTROBJ FSLOPE GETOS GRADE GRSECTION NODE OBSURFACE OGLIST ORTHOMODE OS OSMODE P P0 P1 P2 PL PLI PLI0 PR PRI PRI0 REP STEP SWATH TMP Z0 Z1)
 (vl-load-com)
 (command "._UNDO" "M")
 (command "._UCS" "W")
 (setq CMDECHO (getvar "CMDECHO"))
 (setvar "CMDECHO" 0)
 (setq OSMODE (getvar "OSMODE"))
 (setq ORTHOMODE (getvar "ORTHOMODE"))
 (setvar "ORTHOMODE" 0)
 (setq ANGBASE (getvar "ANGBASE"))
 (setvar "ANGBASE" 0.0)
 (setq ANGDIR (getvar "ANGDIR"))
 (setvar "ANGDIR" 0)

 (defun *error* (msg)
  (if (>= (atof (getvar "ACADVER")) 18.2)
   (command-s "._UCS" "P")
   (command "._UCS" "P")
  )
  (setvar "CMDECHO" CMDECHO)
  (setvar "ANGBASE" ANGBASE)
  (setvar "ANGDIR" ANGDIR)
  (setvar "OSMODE" OSMODE)
  (setvar "ORTHOMODE" ORTHOMODE)
  ;(setq *error* nil)
  (print msg)
 )

 (defun GETOS (/ C P1 P2 P3 P3C P3F P3I P4 P4C P4F P4I)
  (setq P3 (list (/ CWIDTH2 -2.0) Z)
        P3C (list (/ SWATH -2.0) (+ Z (/ (- SWATH CWIDTH2) 2.0 CSLOPE)))
        P3F (list (/ SWATH -2.0) (- Z (/ (- SWATH CWIDTH2) 2.0 FSLOPE)))
        P4 (list (/ CWIDTH2 2.0) Z)
        P4C (list (/ SWATH 2.0) (+ Z (/ (- SWATH CWIDTH2) 2.0 CSLOPE)))
        P4F (list (/ SWATH 2.0) (- Z (/ (- SWATH CWIDTH2) 2.0 FSLOPE)))
  )
  (setq P3I nil P4I nil)
  (setq C 0)
  (while (< (+ C 1) (length OGLIST))
   (setq P1 (nth C OGLIST))
   (setq P2 (nth (+ C 1) OGLIST))
   (if (setq TMP (inters P1 P2 P3 P3C))
    (if (< (car TMP) (/ CWIDTH2 -2.0))
     (setq P3I TMP)
    )
    (if (setq TMP (inters P1 P2 P3 P3F))
     (if (< (car TMP) (/ CWIDTH2 -2.0))
      (setq P3I TMP)
     )
    )
   )
   (if (setq TMP (inters P1 P2 P4 P4C))
    (if (and (> (car TMP) (/ CWIDTH2 2.0))
             (= P4I nil)
        )
     (setq P4I TMP)
    )
    (if (setq TMP (inters P1 P2 P4 P4F))
     (if (and (> (car TMP) (/ CWIDTH2 2.0))
              (= P4I nil)
         )
      (setq P4I TMP)
     )
    )
   )
   (setq C (+ C 1))
  )
  (if (and P3I P3 P4 P4I)
   (list P3I P3 P4 P4I)
   nil
  )
 )
 
 (defun GRSECTION (/ C H NODE P1 P2 P3 P4 PC PB SCALE)
  (setq PC (getvar "VIEWCTR"))
  (setq H (getvar "VIEWSIZE"))
  (setq PB (list (+ (car PC) (/ H 3.0)) (- (cadr PC) (/ H 4.0))))
  (setq SCALE (/ (/ H 2.0) SWATH))
  (setq C 0)
  (setq P1 (nth C OGLIST))
  (setq P1 (list (+ (car PB) (* SCALE (car P1))) (+ (cadr PB) (* SCALE (- (cadr P1) Z)))))
  (while (< (+ C 1) (length OGLIST))
   (progn
    (setq P2 (nth (+ C 1) OGLIST))
    (setq P2 (list (+ (car PB) (* SCALE (car P2))) (+ (cadr PB) (* SCALE (- (cadr P2) Z)))))
    (grdraw P1 P2 -1)
    (setq P1 P2)
    (setq C (+ C 1))
   )
  )
  (if OS
   (progn
    (setq P1 (nth 0 OS))
    (setq P1 (list (+ (car PB) (* SCALE (car P1))) (+ (cadr PB) (* SCALE (- (cadr P1) Z)))))
    (setq P2 (nth 1 OS))
    (setq P2 (list (+ (car PB) (* SCALE (car P2))) (+ (cadr PB) (* SCALE (- (cadr P2) Z)))))
    (grdraw P1 P2 -1)
    (setq P3 (nth 2 OS))
    (setq P3 (list (+ (car PB) (* SCALE (car P3))) (+ (cadr PB) (* SCALE (- (cadr P3) Z)))))
    (grdraw P2 P3 -1)
    (setq P4 (nth 3 OS))
    (setq P4 (list (+ (car PB) (* SCALE (car P4))) (+ (cadr PB) (* SCALE (- (cadr P4) Z)))))
    (grdraw P3 P4 -1)
   )
  )
 )
 
 (defun DIST2D (P1 P2)
  (distance (list (car P1) (cadr P1)) (list (car P2) (cadr P2)))
 )
 
 (if (/= nil (setq OBSURFACE (RFL:GETC3DSURFACE)))
  (if (/= nil (setq P0 (getpoint "\nChannel start point : ")))
   (if (/= nil (setq Z0 (RFL:GETSURFACEPOINT P0 OBSURFACE)))
    (progn
     (setq P0 (list (car P0) (cadr P0)))
     (setq REP (getreal (strcat "\nEnter channel start elevation <" (rtos Z0) "> : ")))
     (if (/= nil REP) (setq Z0 REP))
     (setq P2 (getpoint "\nChannel end point : "))
     (if (/= nil (setq Z2 (RFL:GETSURFACEPOINT P2 OBSURFACE)))
      (progn
       (setq REP (getreal (strcat "\nEnter channel end elevation <" (rtos Z2) "> : ")))
       (if (/= nil REP) (setq Z2 REP))
       (setq GRADE (* 100.0 (/ (- Z2 Z0) (DIST2D P0 P2))))
       (princ (strcat "\nGrade (%) = " (rtos GRADE)))
       (setq GRADE (/ GRADE 100.0))
       (setq SWATH 50.0)
       (setq REP (getreal (strcat "\nEnter swath width <" (rtos SWATH) "> : ")))
       (if (/= nil REP) (setq SWATH REP))
       (setq CSLOPE 2.0)
       (setq REP (getdist (strcat "\nEnter cut slope (X:1) <" (rtos CSLOPE) "> : ")))
       (if (/= nil REP) (setq CSLOPE REP))
       (setq FSLOPE CSLOPE)
       (setq REP (getdist (strcat "\nEnter fill slope (X:1) <" (rtos FSLOPE) "> : ")))
       (if (/= nil REP) (setq FSLOPE REP))
       (setq CWIDTH 2.0)
       (setq REP (getdist (strcat "\nEnter channel width <" (rtos CWIDTH) "> : ")))
       (if (/= nil REP) (setq CWIDTH REP))
       (setq CONTINUE T)
       (setvar "OSMODE" 0)
       ;(command "._PLINE" P0)
       (setq ENTL nil ENT nil ENTR nil)
       ; Get Start Catch Points
       (setq ANG (angle P0 P2))
       (setq PL (list (+ (car P0) (* (/ SWATH 2.0) (cos (+ ANG (/ pi 2.0)))))
                      (+ (cadr P0) (* (/ SWATH 2.0) (sin (+ ANG (/ pi 2.0)))))
                )
       )       
       (setq PR (list (+ (car P0) (* (/ SWATH 2.0) (cos (- ANG (/ pi 2.0)))))
                      (+ (cadr P0) (* (/ SWATH 2.0) (sin (- ANG (/ pi 2.0)))))
                )
       )
       (setq CWIDTH2 CWIDTH)
       (setq OGLIST nil)
       (if (and (/= nil PL) (/= nil PR))
        (progn
         (setq TMP (RFL:GETSURFACELINE PL P0 OBSURFACE))
         (foreach NODE TMP
          (setq OGLIST (append OGLIST (list (list (* -1.0 (DIST2D NODE P0)) (last NODE)))))
         )
         (setq TMP (cdr (RFL:GETSURFACELINE P0 PR OBSURFACE)))
         (foreach NODE TMP
          (setq OGLIST (append OGLIST (list (list (DIST2D NODE P0) (last NODE)))))
         )
        )
       )
       (if OGLIST
        (setq OS (GETOS))
        (setq OS nil)
       )
       (if OS
        (setq PLI0 (list (+ (car P0) (* -1.0 (car (nth 0 OS)) (cos (+ ANG (/ pi 2.0)))))
                         (+ (cadr P0) (* -1.0 (car (nth 0 OS)) (sin (+ ANG (/ pi 2.0)))))
                   )
              PRI0 (list (+ (car P0) (* (car (nth 3 OS)) (cos (- ANG (/ pi 2.0)))))
                         (+ (cadr P0) (* (car (nth 3 OS)) (sin (- ANG (/ pi 2.0)))))
                   )
        )
        (setq PLI0 P0
              PRI0 P0
        )
       )
       ; End Get Start Catch Points
       (princ (strcat "\n" (rtos (* GRADE 100.0)) "%, Point : "))
       (while (and (or (= 5 (car (setq P1 (grread T))))
                       (= 3 (car P1))
                       (= 2 (car P1))
                   )
                   CONTINUE
              )
        (if (= 2 (car P1))
         (if (= 43 (cadr P1))
          (progn
           (setq GRADE (+ GRADE 0.001))
           (princ (strcat "\n" (rtos (* GRADE 100.0)) "%, Point : "))
          )
          (if (= 45 (cadr P1))
           (progn
            (setq GRADE (- GRADE 0.001))
            (princ (strcat "\n" (rtos (* GRADE 100.0)) "%, Point : "))
           )
           (if (= 13 (cadr P1))
            (setq CONTINUE nil)
            (if (= 32 (cadr P1))
             (setq CONTINUE nil)
            )
           )
          )
         )
         (progn
          (setq P (list (caadr P1) (cadadr P1)))
          (setq ANG (/ (+ (angle P0 P) (angle P P2)) 2.0))
          (setq D1 (distance P0 P))
          (setq D2 (distance P P2))
          (setq Z (+ Z0 (* (- Z2 Z0) (/ D1 (+ D1 D2)))))
          (setq PL (list (+ (car P) (* (/ SWATH 2.0) (cos (+ ANG (/ pi 2.0)))))
                         (+ (cadr P) (* (/ SWATH 2.0) (sin (+ ANG (/ pi 2.0)))))
                   )
          )
          (setq PR (list (+ (car P) (* (/ SWATH 2.0) (cos (- ANG (/ pi 2.0)))))
                         (+ (cadr P) (* (/ SWATH 2.0) (sin (- ANG (/ pi 2.0)))))
                   )
          )
          (setq CWIDTH2 (/ CWIDTH (cos (/ (- (angle P P2) (angle P0 P)) 2.0))))
          (setq OGLIST nil)
          (if (and (/= nil PL) (/= nil PR))
           (progn
            (setq TMP (RFL:GETSURFACELINE PL P OBSURFACE))
            (foreach NODE TMP
             (setq OGLIST (append OGLIST (list (list (* -1.0 (DIST2D NODE P)) (last NODE)))))
            )
            (setq TMP (cdr (RFL:GETSURFACELINE P PR OBSURFACE)))
            (foreach NODE TMP
             (setq OGLIST (append OGLIST (list (list (DIST2D NODE P) (last NODE)))))
            )
           )
          )
          (if OGLIST
           (progn
            (setq OS (GETOS))
            (if OS
             (setq PLI (list (+ (car P) (* -1.0 (car (nth 0 OS)) (cos (+ ANG (/ pi 2.0)))))
                             (+ (cadr P) (* -1.0 (car (nth 0 OS)) (sin (+ ANG (/ pi 2.0)))))
                       )
                   PRI (list (+ (car P) (* (car (nth 3 OS)) (cos (- ANG (/ pi 2.0)))))
                             (+ (cadr P) (* (car (nth 3 OS)) (sin (- ANG (/ pi 2.0)))))
                       )
             )
             (setq PLI P
                   PRI P
             )
            )
            (command "'REDRAW")
            (grdraw PL PR -1)
            (GRSECTION)
            (grdraw P0 P -1)
            (grdraw PLI0 PLI -1)
            (grdraw PRI0 PRI -1)
           )
          )
          (if (= 3 (car P1))
           (progn
            (command "'REDRAW")
            (if ENT
             (progn
              (setq C (1+ C))
              (vlax-invoke ENTOBJ 'AddVertex C P)
              (vlax-invoke ENTLOBJ 'AddVertex C PLI)
              (vlax-invoke ENTROBJ 'AddVertex C PRI)
             )
             (progn
              (entmake)
              (entmake (list (cons 0 "LWPOLYLINE")
                             (cons 100 "AcDbEntity")
                             (cons 100 "AcDbPolyline")
                             (cons 90 2)
                             (append (list 10) P0)
                             (append (list 10) P)
                       )
              )
              (setq ENT (entlast))
              (setq ENTOBJ (vlax-ename->vla-object ENT))
              (entmake)
              (entmake (list (cons 0 "LWPOLYLINE")
                             (cons 100 "AcDbEntity")
                             (cons 100 "AcDbPolyline")
                             (cons 90 2)
                             (append (list 10) PLI0)
                             (append (list 10) PLI)
                       )
              )
              (setq ENTL (entlast))
              (setq ENTLOBJ (vlax-ename->vla-object ENTL))
              (entmake)
              (entmake (list (cons 0 "LWPOLYLINE")
                             (cons 100 "AcDbEntity")
                             (cons 100 "AcDbPolyline")
                             (cons 90 2)
                             (append (list 10) PRI0)
                             (append (list 10) PRI)
                       )
              )
              (setq ENTR (entlast))
              (setq ENTROBJ (vlax-ename->vla-object ENTR))
              (setq C 1)
             )
            )
            (setq P0 P
                  Z0 Z
                  PLI0 PLI
                  PRI0 PRI
            )
            (princ (strcat "\n" (rtos (* GRADE 100.0)) "%, Point : "))
           )
          )
         )
        )
       )
      )
     )
    )
   )
  )
 )

 (command "._UCS" "P")
 (setvar "CMDECHO" CMDECHO)
 (setvar "ANGBASE" ANGBASE)
 (setvar "ANGDIR" ANGDIR)
 (setvar "OSMODE" OSMODE)
 (setvar "ORTHOMODE" ORTHOMODE)
 (command "'REDRAW")
 nil
)
