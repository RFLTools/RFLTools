;
;
;     Program Written by Robert LIvingston, 03/03/17
;
;     DUALCAR is a utility for drawing dual carriageway 3D polylines
;
;
(setq RFL:DUALCARLIST
      (list (cons "NORMAL" 2.0)
            (cons "CHOR" "n/a")
            (cons "CVER" "n/a")
            (cons "CSUPER" "n/a")
            (cons "LDF" "1")
            (cons "LDFVAL" 1.0)
            (cons "LDV" "0")
            (cons "LDVVAL" "n/a")
            (cons "LDW" 4.0)
            (cons "MDF" "1")
            (cons "MDFVAL" 1.957)
            (cons "MDV" "0")
            (cons "MDVVAL" "n/a")
            (cons "RDF" "1")
            (cons "RDFVAL" 1.0)
            (cons "RDV" "0")
            (cons "RDVVAL" "n/a")
            (cons "RDW" 4.0)
            (cons "LSD1" 0.25)
            (cons "LSD2" 0.5)
            (cons "RSD1" 0.25)
            (cons "RSD2" 0.5)
            (cons "LCOSF" "1")
            (cons "LCOSFVAL" 19.0)
            (cons "LCOSV" "0")
            (cons "LCOSVVAL" "n/a")
            (cons "RCOSF" "1")
            (cons "RCOSFVAL" 19.0)
            (cons "RCOSV" "0")
            (cons "RCOSVVAL" "n/a")
            (cons "LSOSF" "1")
            (cons "LSOSFVAL" 6.7)
            (cons "LSOSV" "0")
            (cons "LSOSVVAL" "n/a")
            (cons "RSOSF" "1")
            (cons "RSOSFVAL" 6.7)
            (cons "RSOSV" "0")
            (cons "RSOSVVAL" "n/a")
            (cons "LMOSF" "1")
            (cons "LMOSFVAL" 6.2)
            (cons "LMOSV" "0")
            (cons "LMOSVVAL" "n/a")
            (cons "RMOSF" "1")
            (cons "RMOSFVAL" 6.2)
            (cons "RMOSV" "0")
            (cons "RMOSVVAL" "n/a")
            (cons "LVF" "1")
            (cons "LVV" "0")
            (cons "LVVVAL" "n/a")
            (cons "RVF" "1")
            (cons "RVV" "0")
            (cons "RVVVAL" "n/a")
            (cons "LSLOPE1" 6.0)
            (cons "LSLOPE2" 5.0)
            (cons "LSLOPE3" 5.0)
            (cons "LSLOPE4" 5.0)
            (cons "LSLOPE5" 5.0)
            (cons "LSLOPE6" 6.0)
            (cons "RSLOPE1" 6.0)
            (cons "RSLOPE2" 5.0)
            (cons "RSLOPE3" 5.0)
            (cons "RSLOPE4" 5.0)
            (cons "RSLOPE5" 5.0)
            (cons "RSLOPE6" 6.0)
            (cons "LPIVOT4" "0")
            (cons "LPIVOT5" "1")
            (cons "LPIVOT6" "0")
            (cons "RPIVOT4" "0")
            (cons "RPIVOT5" "1")
            (cons "RPIVOT6" "0")
            (cons "DL1" "1")
            (cons "DL2" "1")
            (cons "DL3" "1")
            (cons "DL4" "1")
            (cons "DL5" "1")
            (cons "DL6" "1")
            (cons "DL7" "1")
            (cons "DL8" "1")
            (cons "DL9" "1")
            (cons "DL10" "1")
            (cons "DL11" "0")
            (cons "DL12" "0")
            (cons "DR1" "1")
            (cons "DR2" "1")
            (cons "DR3" "1")
            (cons "DR4" "1")
            (cons "DR5" "1")
            (cons "DR6" "1")
            (cons "DR7" "1")
            (cons "DR8" "1")
            (cons "DR9" "1")
            (cons "DR10" "1")
            (cons "DR11" "0")
            (cons "DR12" "0")
            (cons "FROMTOBEGIN" "1")
            (cons "FROMTOSTARTVAL" 0.0)
            (cons "FROMTOEND" "1")
            (cons "FROMTOENDVAL" 0.0)
            (cons "FROMTOSTEP" 10.0)
            (cons "FROMTOFILE" "0")
      )
)

(defun C:DUALCAR (/ *error* ACCEPTDUALCAR CANCEL CANCELDUALCAR CMDECHO D DCLID INITIATE
                    DUALCARSECTIONLIST DITCHLEFT DITCHMEDIAN DITCHRIGHT LEFTPROF RIGHTPROF
                    GETLINEPERP GETOFFSET
                    ALLEFT ALLEFTSHLDR ALLEFTMDN ALRIGHT ALRIGHTSHLDR ALRIGHTMDN
                    LOS1 LSHLDR LMDN LDITCH MDITCH ROS1 RSHLDR RMDN RDITCH PINWHEEL
                    PL1 PL2 PL3 PL4 PL5 PL6 PL7 PL8 PL9 PL10 PL11 PL12
                    PR1 PR2 PR3 PR4 PR5 PR6 PR7 PR8 PR9 PR10 PR11 PR12
                    SLOPE STA STASTART STAEND STASTEP STOPFLAG SUPERLEFT SUPERRIGHT
                    ALSAVE OSMODE ORTHOMODE PVISAVE SUPERSAVE TOL TMP)
;(defun C:DUALCAR ()

 (setq DUALCARSECTIONLIST nil)

 (command ".UNDO" "M")

 (setq CMDECHO (getvar "CMDECHO"))
 (setvar "CMDECHO" 0)
 (setq ORTHOMODE (getvar "ORTHOMODE"))
 (setvar "ORTHOMODE" 0)
 (setq OSMODE (getvar "OSMODE"))
 (setvar "OSMODE" 0)

 (setq TOL 0.00001)

 (defun PINWHEEL ()
  (if (= PINWHEELCH nil)
   (setq PINWHEELCH "|")
  )
  (setq PINWHEELCH (cond ((= PINWHEELCH "|") "/")
                         ((= PINWHEELCH "/") "-")
                         ((= PINWHEELCH "-") "\\")
                         ((= PINWHEELCH "\\") "|")))
  (princ "\r")
  (princ PINWHEELCH)
 )

 (defun *error* (msg)
  (setq RFL:ALIGNLIST ALSAVE RFL:PVILIST PVISAVE RFL:SUPERLIST SUPERSAVE)
  (if (/= nil STA) (alert (strcat "Error at Station : " (rtos STA 2 3))))
  (setvar "CMDECHO" CMDECHO)
  (setvar "ORTHOMODE" ORTHOMODE)
  (setvar "OSMODE" OSMODE)
  ;(setq *error* nil)
  (princ msg)
 )

; Version 2 of GETOFFSET routine
 (defun GETLINEPERP (P P1 P2 / ANG D D1 D2 D3)
  (setq D (distance P1 P2))
  (setq D1 (distance P1 P))
  (setq D2 (distance P2 P))
  (setq D3 (/ (- (* D1 D1)
                 (* D2 D2)
                 (* D D)
              )
              (* 2.0 D)
           )
  )
  (setq ANG (angle P1 P2))
  (setq P3 (list (+ (nth 0 P2) (* D3 (cos ANG)))
                 (+ (nth 1 P2) (* D3 (sin ANG)))))
 )
 (defun GETOFFSET (STA OFFSET AL / ALSAVE C P P1 P2 P3 P4)
  (setq C 0)
  (setq ALSAVE RFL:ALIGNLIST)
  (setq P1 (RFL:XY (list STA -10.0)))
  (setq P2 (RFL:XY (list STA 10.0)))
  (setq P3 (RFL:XY (list STA OFFSET)))
  (setq RFL:ALIGNLIST AL)
  (setq P (RFL:STAOFF P3))
  (while (and (> (abs (cadr P)) TOL) (< C 100))
   (setq P4 (RFL:XY (list (car P) 0.0)))
   (setq P4 (GETLINEPERP P4 P1 P2))
   (setq P (RFL:STAOFF P4))
   (setq C (+ C 1))
  )
  (setq RFL:ALIGNLIST ALSAVE)
  (if (>= C 100)
   (princ (strcat "\n*** Warning - Maximum number of iterations reached at station " (rtos STA) "\n"))
  )
  (- (cadr (RFL:STAOFF P4)) OFFSET)
 )

; Version 1 of GETOFFSET routine - superseded cuz version 2 works better...
; (defun GETOFFSET (STA OFFSET AL / ALSAVE)
;  (setq P1 (RFL:XY (list STA OFFSET)))
;  (if (= P1 nil)
;   (progn
;    (setq RFL:ALIGNLIST ALSAVE)
;    (eval nil)
;   )
;   (progn
;    (setq ALSAVE RFL:ALIGNLIST)
;    (setq RFL:ALIGNLIST AL)
;    (setq TMP (cadr (RFL:STAOFF P1)))
;    (if (= TMP nil)
;     (progn
;      (setq RFL:ALIGNLIST ALSAVE)
;      (eval nil)
;     )
;     (progn
;      (setq RFL:ALIGNLIST ALSAVE)
;      (setq P3 (RFL:XY (list STA (* -2.0 TMP))))
;      (if (= P3 nil)
;       (progn
;        (setq RFL:ALIGNLIST ALSAVE)
;        (eval nil)
;       )
;       (progn
;        (setq RFL:ALIGNLIST AL)
;        (while (> (distance P1 P3) TOL)
;         (setq P2 (list (/ (+ (car P1) (car P3)) 2.0) (/ (+ (cadr P1) (cadr P3)) 2.0)))
;         (if (> (* (cadr (RFL:STAOFF P2)) (cadr (RFL:STAOFF P3))) 0.0)
;          (setq P3 P2)
;          (setq P1 P2)
;         )
;        )
;        (setq RFL:ALIGNLIST ALSAVE)
;        (- (cadr (RFL:STAOFF P3)) OFFSET)
;       )
;      )
;     )
;    )
;   )
;  )
; )

 (defun INITIATE ()
  (start_image "IMAGE")
  (slide_image 0 0 (- (dimx_tile "IMAGE") 1) (- (dimy_tile "IMAGE") 1) (strcat RFLALIGNSLBNAME "(DUALCAR)"))
  (end_image)
  (set_tile "NORMAL" (rtos (cdr (assoc "NORMAL" RFL:DUALCARLIST))))
  (set_tile "CHOR" (cdr (assoc "CHOR" RFL:DUALCARLIST)))
  (set_tile "CVER" (cdr (assoc "CVER" RFL:DUALCARLIST)))
  (set_tile "CSUPER" (cdr (assoc "CSUPER" RFL:DUALCARLIST)))
  (set_tile "LDF" (cdr (assoc "LDF" RFL:DUALCARLIST)))
  (set_tile "LDFVAL" (rtos (cdr (assoc "LDFVAL" RFL:DUALCARLIST))))
  (set_tile "LDV" (cdr (assoc "LDV" RFL:DUALCARLIST)))
  (set_tile "LDVVAL" (cdr (assoc "LDVVAL" RFL:DUALCARLIST)))
  (set_tile "LDW" (rtos (cdr (assoc "LDW" RFL:DUALCARLIST))))
  (set_tile "MDF" (cdr (assoc "MDF" RFL:DUALCARLIST)))
  (set_tile "MDFVAL" (rtos (cdr (assoc "MDFVAL" RFL:DUALCARLIST))))
  (set_tile "MDV" (cdr (assoc "MDV" RFL:DUALCARLIST)))
  (set_tile "MDVVAL" (cdr (assoc "MDVVAL" RFL:DUALCARLIST)))
  (set_tile "RDF" (cdr (assoc "RDF" RFL:DUALCARLIST)))
  (set_tile "RDFVAL" (rtos (cdr (assoc "RDFVAL" RFL:DUALCARLIST))))
  (set_tile "RDV" (cdr (assoc "RDV" RFL:DUALCARLIST)))
  (set_tile "RDVVAL" (cdr (assoc "RDVVAL" RFL:DUALCARLIST)))
  (set_tile "RDW" (rtos (cdr (assoc "RDW" RFL:DUALCARLIST))))
  (set_tile "LSD1" (rtos (cdr (assoc "LSD1" RFL:DUALCARLIST))))
  (set_tile "LSD2" (rtos (cdr (assoc "LSD2" RFL:DUALCARLIST))))
  (set_tile "RSD1" (rtos (cdr (assoc "RSD1" RFL:DUALCARLIST))))
  (set_tile "RSD2" (rtos (cdr (assoc "RSD2" RFL:DUALCARLIST))))
  (set_tile "LCOSF" (cdr (assoc "LCOSF" RFL:DUALCARLIST)))
  (set_tile "LCOSFVAL" (rtos (cdr (assoc "LCOSFVAL" RFL:DUALCARLIST))))
  (set_tile "LCOSV" (cdr (assoc "LCOSV" RFL:DUALCARLIST)))
  (set_tile "LCOSVVAL" (cdr (assoc "LCOSVVAL" RFL:DUALCARLIST)))
  (set_tile "RCOSF" (cdr (assoc "RCOSF" RFL:DUALCARLIST)))
  (set_tile "RCOSFVAL" (rtos (cdr (assoc "RCOSFVAL" RFL:DUALCARLIST))))
  (set_tile "RCOSV" (cdr (assoc "RCOSV" RFL:DUALCARLIST)))
  (set_tile "RCOSVVAL" (cdr (assoc "RCOSVVAL" RFL:DUALCARLIST)))
  (set_tile "LSOSF" (cdr (assoc "LSOSF" RFL:DUALCARLIST)))
  (set_tile "LSOSFVAL" (rtos (cdr (assoc "LSOSFVAL" RFL:DUALCARLIST))))
  (set_tile "LSOSV" (cdr (assoc "LSOSV" RFL:DUALCARLIST)))
  (set_tile "LSOSVVAL" (cdr (assoc "LSOSVVAL" RFL:DUALCARLIST)))
  (set_tile "RSOSF" (cdr (assoc "RSOSF" RFL:DUALCARLIST)))
  (set_tile "RSOSFVAL" (rtos (cdr (assoc "RSOSFVAL" RFL:DUALCARLIST))))
  (set_tile "RSOSV" (cdr (assoc "RSOSV" RFL:DUALCARLIST)))
  (set_tile "RSOSVVAL" (cdr (assoc "RSOSVVAL" RFL:DUALCARLIST)))
  (set_tile "LMOSF" (cdr (assoc "LMOSF" RFL:DUALCARLIST)))
  (set_tile "LMOSFVAL" (rtos (cdr (assoc "LMOSFVAL" RFL:DUALCARLIST))))
  (set_tile "LMOSV" (cdr (assoc "LMOSV" RFL:DUALCARLIST)))
  (set_tile "LMOSVVAL" (cdr (assoc "LMOSVVAL" RFL:DUALCARLIST)))
  (set_tile "RMOSF" (cdr (assoc "RMOSF" RFL:DUALCARLIST)))
  (set_tile "RMOSFVAL" (rtos (cdr (assoc "RMOSFVAL" RFL:DUALCARLIST))))
  (set_tile "RMOSV" (cdr (assoc "RMOSV" RFL:DUALCARLIST)))
  (set_tile "RMOSVVAL" (cdr (assoc "RMOSVVAL" RFL:DUALCARLIST)))
  (set_tile "LVF" (cdr (assoc "LVF" RFL:DUALCARLIST)))
  (set_tile "LVV" (cdr (assoc "LVV" RFL:DUALCARLIST)))
  (set_tile "LVVVAL" (cdr (assoc "LVVVAL" RFL:DUALCARLIST)))
  (set_tile "RVF" (cdr (assoc "RVF" RFL:DUALCARLIST)))
  (set_tile "RVV" (cdr (assoc "RVV" RFL:DUALCARLIST)))
  (set_tile "RVVVAL" (cdr (assoc "RVVVAL" RFL:DUALCARLIST)))
  (set_tile "LSLOPE1" (rtos (cdr (assoc "LSLOPE1" RFL:DUALCARLIST))))
  (set_tile "LSLOPE2" (rtos (cdr (assoc "LSLOPE2" RFL:DUALCARLIST))))
  (set_tile "LSLOPE3" (rtos (cdr (assoc "LSLOPE3" RFL:DUALCARLIST))))
  (set_tile "LSLOPE4" (rtos (cdr (assoc "LSLOPE4" RFL:DUALCARLIST))))
  (set_tile "LSLOPE5" (rtos (cdr (assoc "LSLOPE5" RFL:DUALCARLIST))))
  (set_tile "LSLOPE6" (rtos (cdr (assoc "LSLOPE6" RFL:DUALCARLIST))))
  (set_tile "RSLOPE1" (rtos (cdr (assoc "RSLOPE1" RFL:DUALCARLIST))))
  (set_tile "RSLOPE2" (rtos (cdr (assoc "RSLOPE2" RFL:DUALCARLIST))))
  (set_tile "RSLOPE3" (rtos (cdr (assoc "RSLOPE3" RFL:DUALCARLIST))))
  (set_tile "RSLOPE4" (rtos (cdr (assoc "RSLOPE4" RFL:DUALCARLIST))))
  (set_tile "RSLOPE5" (rtos (cdr (assoc "RSLOPE5" RFL:DUALCARLIST))))
  (set_tile "RSLOPE6" (rtos (cdr (assoc "RSLOPE6" RFL:DUALCARLIST))))
  (set_tile "LPIVOT4" (cdr (assoc "LPIVOT4" RFL:DUALCARLIST)))
  (set_tile "LPIVOT5" (cdr (assoc "LPIVOT5" RFL:DUALCARLIST)))
  (set_tile "LPIVOT6" (cdr (assoc "LPIVOT6" RFL:DUALCARLIST)))
  (set_tile "RPIVOT4" (cdr (assoc "RPIVOT4" RFL:DUALCARLIST)))
  (set_tile "RPIVOT5" (cdr (assoc "RPIVOT5" RFL:DUALCARLIST)))
  (set_tile "RPIVOT6" (cdr (assoc "RPIVOT6" RFL:DUALCARLIST)))
  (set_tile "DL1" (cdr (assoc "DL1" RFL:DUALCARLIST)))
  (set_tile "DL2" (cdr (assoc "DL2" RFL:DUALCARLIST)))
  (set_tile "DL3" (cdr (assoc "DL3" RFL:DUALCARLIST)))
  (set_tile "DL4" (cdr (assoc "DL4" RFL:DUALCARLIST)))
  (set_tile "DL5" (cdr (assoc "DL5" RFL:DUALCARLIST)))
  (set_tile "DL6" (cdr (assoc "DL6" RFL:DUALCARLIST)))
  (set_tile "DL7" (cdr (assoc "DL7" RFL:DUALCARLIST)))
  (set_tile "DL8" (cdr (assoc "DL8" RFL:DUALCARLIST)))
  (set_tile "DL9" (cdr (assoc "DL9" RFL:DUALCARLIST)))
  (set_tile "DL10" (cdr (assoc "DL10" RFL:DUALCARLIST)))
  (set_tile "DL11" (cdr (assoc "DL11" RFL:DUALCARLIST)))
  (set_tile "DL12" (cdr (assoc "DL12" RFL:DUALCARLIST)))
  (set_tile "DR1" (cdr (assoc "DR1" RFL:DUALCARLIST)))
  (set_tile "DR2" (cdr (assoc "DR2" RFL:DUALCARLIST)))
  (set_tile "DR3" (cdr (assoc "DR3" RFL:DUALCARLIST)))
  (set_tile "DR4" (cdr (assoc "DR4" RFL:DUALCARLIST)))
  (set_tile "DR5" (cdr (assoc "DR5" RFL:DUALCARLIST)))
  (set_tile "DR6" (cdr (assoc "DR6" RFL:DUALCARLIST)))
  (set_tile "DR7" (cdr (assoc "DR7" RFL:DUALCARLIST)))
  (set_tile "DR8" (cdr (assoc "DR8" RFL:DUALCARLIST)))
  (set_tile "DR9" (cdr (assoc "DR9" RFL:DUALCARLIST)))
  (set_tile "DR10" (cdr (assoc "DR10" RFL:DUALCARLIST)))
  (set_tile "DR11" (cdr (assoc "DR11" RFL:DUALCARLIST)))
  (set_tile "DR12" (cdr (assoc "DR12" RFL:DUALCARLIST)))
  (set_tile "FROMTOBEGIN" (cdr (assoc "FROMTOBEGIN" RFL:DUALCARLIST)))
  (set_tile "FROMTOSTARTVAL" (rtos (cdr (assoc "FROMTOSTARTVAL" RFL:DUALCARLIST))))
  (set_tile "FROMTOEND" (cdr (assoc "FROMTOEND" RFL:DUALCARLIST)))
  (set_tile "FROMTOENDVAL" (rtos (cdr (assoc "FROMTOENDVAL" RFL:DUALCARLIST))))
  (set_tile "FROMTOSTEP" (rtos (cdr (assoc "FROMTOSTEP" RFL:DUALCARLIST))))
  (set_tile "FROMTOFILE" (cdr (assoc "FROMTOFILE" RFL:DUALCARLIST)))
 )

 (defun SETENABLED ()
  (if (= (get_tile "LDF") "1")
   (progn
    (mode_tile "LDFVAL" 0)
    (mode_tile "LDVVAL" 1)
    (mode_tile "LDVPICK" 1)
   )
   (progn
    (mode_tile "LDFVAL" 1)
    (mode_tile "LDVVAL" 0)
    (mode_tile "LDVPICK" 0)
   )
  )
  (if (= (get_tile "MDF") "1")
   (progn
    (mode_tile "MDFVAL" 0)
    (mode_tile "MDVVAL" 1)
    (mode_tile "MDVPICK" 1)
   )
   (progn
    (mode_tile "MDFVAL" 1)
    (mode_tile "MDVVAL" 0)
    (mode_tile "MDVPICK" 0)
   )
  )
  (if (= (get_tile "RDF") "1")
   (progn
    (mode_tile "RDFVAL" 0)
    (mode_tile "RDVVAL" 1)
    (mode_tile "RDVPICK" 1)
   )
   (progn
    (mode_tile "RDFVAL" 1)
    (mode_tile "RDVVAL" 0)
    (mode_tile "RDVPICK" 0)
   )
  )
  (if (= (get_tile "LCOSF") "1")
   (progn
    (mode_tile "LCOSFVAL" 0)
    (mode_tile "LCOSVVAL" 1)
    (mode_tile "LCOSVPICK" 1)
   )
   (progn
    (mode_tile "LCOSFVAL" 1)
    (mode_tile "LCOSVVAL" 0)
    (mode_tile "LCOSVPICK" 0)
   )
  )
  (if (= (get_tile "RCOSF") "1")
   (progn
    (mode_tile "RCOSFVAL" 0)
    (mode_tile "RCOSVVAL" 1)
    (mode_tile "RCOSVPICK" 1)
   )
   (progn
    (mode_tile "RCOSFVAL" 1)
    (mode_tile "RCOSVVAL" 0)
    (mode_tile "RCOSVPICK" 0)
   )
  )
  (if (= (get_tile "LSOSF") "1")
   (progn
    (mode_tile "LSOSFVAL" 0)
    (mode_tile "LSOSVVAL" 1)
    (mode_tile "LSOSVPICK" 1)
   )
   (progn
    (mode_tile "LSOSFVAL" 1)
    (mode_tile "LSOSVVAL" 0)
    (mode_tile "LSOSVPICK" 0)
   )
  )
  (if (= (get_tile "RSOSF") "1")
   (progn
    (mode_tile "RSOSFVAL" 0)
    (mode_tile "RSOSVVAL" 1)
    (mode_tile "RSOSVPICK" 1)
   )
   (progn
    (mode_tile "RSOSFVAL" 1)
    (mode_tile "RSOSVVAL" 0)
    (mode_tile "RSOSVPICK" 0)
   )
  )
  (if (= (get_tile "LMOSF") "1")
   (progn
    (mode_tile "LMOSFVAL" 0)
    (mode_tile "LMOSVVAL" 1)
    (mode_tile "LMOSVPICK" 1)
   )
   (progn
    (mode_tile "LMOSFVAL" 1)
    (mode_tile "LMOSVVAL" 0)
    (mode_tile "LMOSVPICK" 0)
   )
  )
  (if (= (get_tile "RMOSF") "1")
   (progn
    (mode_tile "RMOSFVAL" 0)
    (mode_tile "RMOSVVAL" 1)
    (mode_tile "RMOSVPICK" 1)
   )
   (progn
    (mode_tile "RMOSFVAL" 1)
    (mode_tile "RMOSVVAL" 0)
    (mode_tile "RMOSVPICK" 0)
   )
  )
  (if (= (get_tile "LVF") "1")
   (progn
    (mode_tile "LVVVAL" 1)
    (mode_tile "LVVPICK" 1)
   )
   (progn
    (mode_tile "LVVVAL" 0)
    (mode_tile "LVVPICK" 0)
   )
  )
  (if (= (get_tile "RVF") "1")
   (progn
    (mode_tile "RVVVAL" 1)
    (mode_tile "RVVPICK" 1)
   )
   (progn
    (mode_tile "RVVVAL" 0)
    (mode_tile "RVVPICK" 0)
   )
  )
  (if (= (get_tile "FROMTOBEGIN") "1")
   (progn
    (mode_tile "FROMTOSTARTVAL" 1)
   )
   (progn
    (mode_tile "FROMTOSTARTVAL" 0)
   )
  )
  (if (= (get_tile "FROMTOEND") "1")
   (progn
    (mode_tile "FROMTOENDVAL" 1)
   )
   (progn
    (mode_tile "FROMTOENDVAL" 0)
   )
  )
 )

 (defun PICKFILE (TILE EXT / FILENAME)
  (cond ((= EXT ".HOR")
         (progn
          (if (= (vl-registry-read "HKEY_CURRENT_USER\\rflAlignDirectory") nil)
           (vl-registry-write "HKEY_CURRENT_USER\\rflAlignDirectory" "" "")
          )
          (setq FILENAME (getfiled "Select a Horizontal Alignment File" (vl-registry-read "HKEY_CURRENT_USER\\rflAlignDirectory") "hor" 2))
          (if (= nil FILENAME)
           (set_tile TILE "n/a")
           (progn
            (set_tile TILE (strcase FILENAME))
            (vl-registry-write "HKEY_CURRENT_USER\\rflAlignDirectory" "" (strcat (vl-filename-directory FILENAME) "\\"))
           )
          )
         )
        )
        ((= EXT ".VRT")
         (progn
          (if (= (vl-registry-read "HKEY_CURRENT_USER\\rflAlignDirectory") nil)
           (vl-registry-write "HKEY_CURRENT_USER\\rflAlignDirectory" "" "")
          )
          (setq FILENAME (getfiled "Select a Vertical Alignment File" (vl-registry-read "HKEY_CURRENT_USER\\rflAlignDirectory") "vrt" 2))
          (if (= nil FILENAME)
           (set_tile TILE "n/a")
           (progn
            (set_tile TILE (strcase FILENAME))
            (vl-registry-write "HKEY_CURRENT_USER\\rflAlignDirectory" "" (strcat (vl-filename-directory FILENAME) "\\"))
           )
          )
         )
        )
        ((= EXT ".E")
         (progn
          (if (= (vl-registry-read "HKEY_CURRENT_USER\\rflAlignDirectory") nil)
           (vl-registry-write "HKEY_CURRENT_USER\\rflAlignDirectory" "" "")
          )
          (setq FILENAME (getfiled "Select a Superelevation File" (vl-registry-read "HKEY_CURRENT_USER\\rflAlignDirectory") "e" 2))
          (if (= nil FILENAME)
           (set_tile TILE "n/a")
           (progn
            (set_tile TILE (strcase FILENAME))
            (vl-registry-write "HKEY_CURRENT_USER\\rflAlignDirectory" "" (strcat (vl-filename-directory FILENAME) "\\"))
           )
          )
         )
        )
  )
 )

 (defun CHECKFILE (TILE EXT / FILENAME)
  (setq FILENAME (strcase (get_tile TILE)))
  (if (< (strlen FILENAME) (strlen EXT))
   (set_tile TILE "n/a")
   (if (/= EXT (substr FILENAME (1+ (- (strlen FILENAME) (strlen EXT)))))
    (set_tile TILE "n/a")
    (if (= nil (setq FILENAME (findfile FILENAME)))
     (set_tile TILE "n/a")
     (set_tile TILE FILENAME)
    )
   )
  )
 )

 (defun FIXNUMBER (TILE)
  (set_tile TILE (rtos (atof (get_tile TILE))))
 )

 (defun WRITESETTINGS (/ OUTFILE)
  (if (= (vl-registry-read "HKEY_CURRENT_USER\\rflAlignDirectory") nil)
   (vl-registry-write "HKEY_CURRENT_USER\\rflAlignDirectory" "" "")
  )
  (setq OUTFILE (getfiled "Select a file for saving" (vl-registry-read "HKEY_CURRENT_USER\\rflAlignDirectory") "ini" 1))
  (if (/= OUTFILE nil)
   (progn
    (vl-registry-write "HKEY_CURRENT_USER\\rflAlignDirectory" "" (strcat (vl-filename-directory OUTFILE) "\\"))
    (setq OUTFILE (open OUTFILE "w"))
    (princ ";\n" OUTFILE)
    (princ "; RFL DualCar settings file\n" OUTFILE)
    (princ ";\n" OUTFILE)
    (princ (strcat "NORMAL:" (get_tile "NORMAL") "\n") OUTFILE)
    (princ (strcat "CHOR:" (get_tile "CHOR") "\n") OUTFILE)
    (princ (strcat "CVER:" (get_tile "CVER") "\n") OUTFILE)
    (princ (strcat "CSUPER:" (get_tile "CSUPER") "\n") OUTFILE)
    (princ (strcat "LDF:" (get_tile "LDF") "\n") OUTFILE)
    (princ (strcat "LDFVAL:" (get_tile "LDFVAL") "\n") OUTFILE)
    (princ (strcat "LDV:" (get_tile "LDV") "\n") OUTFILE)
    (princ (strcat "LDVVAL:" (get_tile "LDVVAL") "\n") OUTFILE)
    (princ (strcat "LDW:" (get_tile "LDW") "\n") OUTFILE)
    (princ (strcat "MDF:" (get_tile "MDF") "\n") OUTFILE)
    (princ (strcat "MDFVAL:" (get_tile "MDFVAL") "\n") OUTFILE)
    (princ (strcat "MDV:" (get_tile "MDV") "\n") OUTFILE)
    (princ (strcat "MDVVAL:" (get_tile "MDVVAL") "\n") OUTFILE)
    (princ (strcat "RDF:" (get_tile "RDF") "\n") OUTFILE)
    (princ (strcat "RDFVAL:" (get_tile "RDFVAL") "\n") OUTFILE)
    (princ (strcat "RDV:" (get_tile "RDV") "\n") OUTFILE)
    (princ (strcat "RDVVAL:" (get_tile "RDVVAL") "\n") OUTFILE)
    (princ (strcat "RDW:" (get_tile "RDW") "\n") OUTFILE)
    (princ (strcat "LSD1:" (get_tile "LSD1") "\n") OUTFILE)
    (princ (strcat "LSD2:" (get_tile "LSD2") "\n") OUTFILE)
    (princ (strcat "RSD1:" (get_tile "RSD1") "\n") OUTFILE)
    (princ (strcat "RSD2:" (get_tile "RSD2") "\n") OUTFILE)
    (princ (strcat "LCOSF:" (get_tile "LCOSF") "\n") OUTFILE)
    (princ (strcat "LCOSFVAL:" (get_tile "LCOSFVAL") "\n") OUTFILE)
    (princ (strcat "LCOSV:" (get_tile "LCOSV") "\n") OUTFILE)
    (princ (strcat "LCOSVVAL:" (get_tile "LCOSVVAL") "\n") OUTFILE)
    (princ (strcat "RCOSF:" (get_tile "RCOSF") "\n") OUTFILE)
    (princ (strcat "RCOSFVAL:" (get_tile "RCOSFVAL") "\n") OUTFILE)
    (princ (strcat "RCOSV:" (get_tile "RCOSV") "\n") OUTFILE)
    (princ (strcat "RCOSVVAL:" (get_tile "RCOSVVAL") "\n") OUTFILE)
    (princ (strcat "LSOSF:" (get_tile "LSOSF") "\n") OUTFILE)
    (princ (strcat "LSOSFVAL:" (get_tile "LSOSFVAL") "\n") OUTFILE)
    (princ (strcat "LSOSV:" (get_tile "LSOSV") "\n") OUTFILE)
    (princ (strcat "LSOSVVAL:" (get_tile "LSOSVVAL") "\n") OUTFILE)
    (princ (strcat "RSOSF:" (get_tile "RSOSF") "\n") OUTFILE)
    (princ (strcat "RSOSFVAL:" (get_tile "RSOSFVAL") "\n") OUTFILE)
    (princ (strcat "RSOSV:" (get_tile "RSOSV") "\n") OUTFILE)
    (princ (strcat "RSOSVVAL:" (get_tile "RSOSVVAL") "\n") OUTFILE)
    (princ (strcat "LMOSF:" (get_tile "LMOSF") "\n") OUTFILE)
    (princ (strcat "LMOSFVAL:" (get_tile "LMOSFVAL") "\n") OUTFILE)
    (princ (strcat "LMOSV:" (get_tile "LMOSV") "\n") OUTFILE)
    (princ (strcat "LMOSVVAL:" (get_tile "LMOSVVAL") "\n") OUTFILE)
    (princ (strcat "RMOSF:" (get_tile "RMOSF") "\n") OUTFILE)
    (princ (strcat "RMOSFVAL:" (get_tile "RMOSFVAL") "\n") OUTFILE)
    (princ (strcat "RMOSV:" (get_tile "RMOSV") "\n") OUTFILE)
    (princ (strcat "RMOSVVAL:" (get_tile "RMOSVVAL") "\n") OUTFILE)
    (princ (strcat "LVF:" (get_tile "LVF") "\n") OUTFILE)
    (princ (strcat "LVV:" (get_tile "LVV") "\n") OUTFILE)
    (princ (strcat "LVVVAL:" (get_tile "LVVVAL") "\n") OUTFILE)
    (princ (strcat "RVF:" (get_tile "RVF") "\n") OUTFILE)
    (princ (strcat "RVV:" (get_tile "RVV") "\n") OUTFILE)
    (princ (strcat "RVVVAL:" (get_tile "RVVVAL") "\n") OUTFILE)
    (princ (strcat "LSLOPE1:" (get_tile "LSLOPE1") "\n") OUTFILE)
    (princ (strcat "LSLOPE2:" (get_tile "LSLOPE2") "\n") OUTFILE)
    (princ (strcat "LSLOPE3:" (get_tile "LSLOPE3") "\n") OUTFILE)
    (princ (strcat "LSLOPE4:" (get_tile "LSLOPE4") "\n") OUTFILE)
    (princ (strcat "LSLOPE5:" (get_tile "LSLOPE5") "\n") OUTFILE)
    (princ (strcat "LSLOPE6:" (get_tile "LSLOPE6") "\n") OUTFILE)
    (princ (strcat "RSLOPE1:" (get_tile "RSLOPE1") "\n") OUTFILE)
    (princ (strcat "RSLOPE2:" (get_tile "RSLOPE2") "\n") OUTFILE)
    (princ (strcat "RSLOPE3:" (get_tile "RSLOPE3") "\n") OUTFILE)
    (princ (strcat "RSLOPE4:" (get_tile "RSLOPE4") "\n") OUTFILE)
    (princ (strcat "RSLOPE5:" (get_tile "RSLOPE5") "\n") OUTFILE)
    (princ (strcat "RSLOPE6:" (get_tile "RSLOPE6") "\n") OUTFILE)
    (princ (strcat "LPIVOT4:" (get_tile "LPIVOT4") "\n") OUTFILE)
    (princ (strcat "LPIVOT5:" (get_tile "LPIVOT5") "\n") OUTFILE)
    (princ (strcat "LPIVOT6:" (get_tile "LPIVOT6") "\n") OUTFILE)
    (princ (strcat "RPIVOT4:" (get_tile "RPIVOT4") "\n") OUTFILE)
    (princ (strcat "RPIVOT5:" (get_tile "RPIVOT5") "\n") OUTFILE)
    (princ (strcat "RPIVOT6:" (get_tile "RPIVOT6") "\n") OUTFILE)
    (princ (strcat "DL1:" (get_tile "DL1") "\n") OUTFILE)
    (princ (strcat "DL2:" (get_tile "DL2") "\n") OUTFILE)
    (princ (strcat "DL3:" (get_tile "DL3") "\n") OUTFILE)
    (princ (strcat "DL4:" (get_tile "DL4") "\n") OUTFILE)
    (princ (strcat "DL5:" (get_tile "DL5") "\n") OUTFILE)
    (princ (strcat "DL6:" (get_tile "DL6") "\n") OUTFILE)
    (princ (strcat "DL7:" (get_tile "DL7") "\n") OUTFILE)
    (princ (strcat "DL8:" (get_tile "DL8") "\n") OUTFILE)
    (princ (strcat "DL9:" (get_tile "DL9") "\n") OUTFILE)
    (princ (strcat "DL10:" (get_tile "DL10") "\n") OUTFILE)
    (princ (strcat "DL11:" (get_tile "DL11") "\n") OUTFILE)
    (princ (strcat "DL12:" (get_tile "DL12") "\n") OUTFILE)
    (princ (strcat "DR1:" (get_tile "DR1") "\n") OUTFILE)
    (princ (strcat "DR2:" (get_tile "DR2") "\n") OUTFILE)
    (princ (strcat "DR3:" (get_tile "DR3") "\n") OUTFILE)
    (princ (strcat "DR4:" (get_tile "DR4") "\n") OUTFILE)
    (princ (strcat "DR5:" (get_tile "DR5") "\n") OUTFILE)
    (princ (strcat "DR6:" (get_tile "DR6") "\n") OUTFILE)
    (princ (strcat "DR7:" (get_tile "DR7") "\n") OUTFILE)
    (princ (strcat "DR8:" (get_tile "DR8") "\n") OUTFILE)
    (princ (strcat "DR9:" (get_tile "DR9") "\n") OUTFILE)
    (princ (strcat "DR10:" (get_tile "DR10") "\n") OUTFILE)
    (princ (strcat "DR11:" (get_tile "DR11") "\n") OUTFILE)
    (princ (strcat "DR12:" (get_tile "DR12") "\n") OUTFILE)
    (princ (strcat "FROMTOBEGIN:" (get_tile "FROMTOBEGIN") "\n") OUTFILE)
    (princ (strcat "FROMTOSTARTVAL:" (get_tile "FROMTOSTARTVAL") "\n") OUTFILE)
    (princ (strcat "FROMTOEND:" (get_tile "FROMTOEND") "\n") OUTFILE)
    (princ (strcat "FROMTOENDVAL:" (get_tile "FROMTOENDVAL") "\n") OUTFILE)
    (princ (strcat "FROMTOSTEP:" (get_tile "FROMTOSTEP") "\n") OUTFILE)
    (princ (strcat "FROMTOFILE:" (get_tile "FROMTOFILE") "\n") OUTFILE)
    (close OUTFILE)
   )
  )
 )

 (defun READSETTINGS (/ INFILE INLINE P TILE TXT)
  (if (= (vl-registry-read "HKEY_CURRENT_USER\\rflAlignDirectory") nil)
   (vl-registry-write "HKEY_CURRENT_USER\\rflAlignDirectory" "" "")
  )
  (setq INFILE (getfiled "Select a file for reading" (vl-registry-read "HKEY_CURRENT_USER\\rflAlignDirectory") "ini" 2))
  (if (/= INFILE nil)
   (progn
    (setq INFILE (open INFILE "r"))
    (while (/= nil (setq INLINE (read-line INFILE)))
     (setq P (vl-string-search ":" INLINE))
     (if (/= P nil)
      (progn
       (setq TILE (substr INLINE 1 P))
       (setq TXT (substr INLINE (+ 2 P)))
       (set_tile TILE TXT)
      )
     )
    )
    (close INFILE)
   )
  )
  (SETENABLED)
 )

 (defun ACCEPTDUALCAR ()
  (setq CANCEL 0)
  (setq RFL:DUALCARLIST
        (list (cons "NORMAL" (atof (get_tile "NORMAL")))
              (cons "CHOR" (get_tile "CHOR"))
              (cons "CVER" (get_tile "CVER"))
              (cons "CSUPER" (get_tile "CSUPER"))
              (cons "LDF" (get_tile "LDF"))
              (cons "LDFVAL" (atof (get_tile "LDFVAL")))
              (cons "LDV" (get_tile "LDV"))
              (cons "LDVVAL" (get_tile "LDVVAL"))
              (cons "LDW" (atof (get_tile "LDW")))
              (cons "MDF" (get_tile "MDF"))
              (cons "MDFVAL" (atof (get_tile "MDFVAL")))
              (cons "MDV" (get_tile "MDV"))
              (cons "MDVVAL" (get_tile "MDVVAL"))
              (cons "RDF" (get_tile "RDF"))
              (cons "RDFVAL" (atof (get_tile "RDFVAL")))
              (cons "RDV" (get_tile "RDV"))
              (cons "RDVVAL" (get_tile "RDVVAL"))
              (cons "RDW" (atof (get_tile "RDW")))
              (cons "LSD1" (atof (get_tile "LSD1")))
              (cons "LSD2" (atof (get_tile "LSD2")))
              (cons "RSD1" (atof (get_tile "RSD1")))
              (cons "RSD2" (atof (get_tile "RSD2")))
              (cons "LCOSF" (get_tile "LCOSF"))
              (cons "LCOSFVAL" (atof (get_tile "LCOSFVAL")))
              (cons "LCOSV" (get_tile "LCOSV"))
              (cons "LCOSVVAL" (get_tile "LCOSVVAL"))
              (cons "RCOSF" (get_tile "RCOSF"))
              (cons "RCOSFVAL" (atof (get_tile "RCOSFVAL")))
              (cons "RCOSV" (get_tile "RCOSV"))
              (cons "RCOSVVAL" (get_tile "RCOSVVAL"))
              (cons "LSOSF" (get_tile "LSOSF"))
              (cons "LSOSFVAL" (atof (get_tile "LSOSFVAL")))
              (cons "LSOSV" (get_tile "LSOSV"))
              (cons "LSOSVVAL" (get_tile "LSOSVVAL"))
              (cons "RSOSF" (get_tile "RSOSF"))
              (cons "RSOSFVAL" (atof (get_tile "RSOSFVAL")))
              (cons "RSOSV" (get_tile "RSOSV"))
              (cons "RSOSVVAL" (get_tile "RSOSVVAL"))
              (cons "LMOSF" (get_tile "LMOSF"))
              (cons "LMOSFVAL" (atof (get_tile "LMOSFVAL")))
              (cons "LMOSV" (get_tile "LMOSV"))
              (cons "LMOSVVAL" (get_tile "LMOSVVAL"))
              (cons "RMOSF" (get_tile "RMOSF"))
              (cons "RMOSFVAL" (atof (get_tile "RMOSFVAL")))
              (cons "RMOSV" (get_tile "RMOSV"))
              (cons "RMOSVVAL" (get_tile "RMOSVVAL"))
              (cons "LVF" (get_tile "LVF"))
              (cons "LVV" (get_tile "LVV"))
              (cons "LVVVAL" (get_tile "LVVVAL"))
              (cons "RVF" (get_tile "RVF"))
              (cons "RVV" (get_tile "RVV"))
              (cons "RVVVAL" (get_tile "RVVVAL"))
              (cons "LSLOPE1" (atof (get_tile "LSLOPE1")))
              (cons "LSLOPE2" (atof (get_tile "LSLOPE2")))
              (cons "LSLOPE3" (atof (get_tile "LSLOPE3")))
              (cons "LSLOPE4" (atof (get_tile "LSLOPE4")))
              (cons "LSLOPE5" (atof (get_tile "LSLOPE5")))
              (cons "LSLOPE6" (atof (get_tile "LSLOPE6")))
              (cons "RSLOPE1" (atof (get_tile "RSLOPE1")))
              (cons "RSLOPE2" (atof (get_tile "RSLOPE2")))
              (cons "RSLOPE3" (atof (get_tile "RSLOPE3")))
              (cons "RSLOPE4" (atof (get_tile "RSLOPE4")))
              (cons "RSLOPE5" (atof (get_tile "RSLOPE5")))
              (cons "RSLOPE6" (atof (get_tile "RSLOPE6")))
              (cons "LPIVOT4" (get_tile "LPIVOT4"))
              (cons "LPIVOT5" (get_tile "LPIVOT5"))
              (cons "LPIVOT6" (get_tile "LPIVOT6"))
              (cons "RPIVOT4" (get_tile "RPIVOT4"))
              (cons "RPIVOT5" (get_tile "RPIVOT5"))
              (cons "RPIVOT6" (get_tile "RPIVOT6"))
              (cons "DL1" (get_tile "DL1"))
              (cons "DL2" (get_tile "DL2"))
              (cons "DL3" (get_tile "DL3"))
              (cons "DL4" (get_tile "DL4"))
              (cons "DL5" (get_tile "DL5"))
              (cons "DL6" (get_tile "DL6"))
              (cons "DL7" (get_tile "DL7"))
              (cons "DL8" (get_tile "DL8"))
              (cons "DL9" (get_tile "DL9"))
              (cons "DL10" (get_tile "DL10"))
              (cons "DL11" (get_tile "DL11"))
              (cons "DL12" (get_tile "DL12"))
              (cons "DR1" (get_tile "DR1"))
              (cons "DR2" (get_tile "DR2"))
              (cons "DR3" (get_tile "DR3"))
              (cons "DR4" (get_tile "DR4"))
              (cons "DR5" (get_tile "DR5"))
              (cons "DR6" (get_tile "DR6"))
              (cons "DR7" (get_tile "DR7"))
              (cons "DR8" (get_tile "DR8"))
              (cons "DR9" (get_tile "DR9"))
              (cons "DR10" (get_tile "DR10"))
              (cons "DR11" (get_tile "DR11"))
              (cons "DR12" (get_tile "DR12"))
              (cons "FROMTOBEGIN" (get_tile "FROMTOBEGIN"))
              (cons "FROMTOSTARTVAL" (atof (get_tile "FROMTOSTARTVAL")))
              (cons "FROMTOEND" (get_tile "FROMTOEND"))
              (cons "FROMTOENDVAL" (atof (get_tile "FROMTOENDVAL")))
              (cons "FROMTOSTEP" (atof (get_tile "FROMTOSTEP")))
              (cons "FROMTOFILE" (get_tile "FROMTOFILE"))
      )
  )
  (done_dialog)
  (unload_dialog DCL_ID)
 )

 (defun CANCELDUALCAR ()
  (setq CANCEL 1)
  (done_dialog)
  (unload_dialog DCL_ID)
 )

 (setq RFLALIGNSLBNAME "rflAlign.slb")
 (if (= nil (findfile RFLALIGNSLBNAME))
  (progn
   (setq RFLALIGNSLBNAME (vl-filename-mktemp "rfl.slb"))
   (RFL:MAKERFLSLB RFLALIGNSLBNAME)
  )
 )
 (if (= DUALCARDCLNAME nil)
  (progn
   (setq DUALCARDCLNAME (vl-filename-mktemp "rfl.dcl"))
   (RFL:MAKEDCL DUALCARDCLNAME "DUALCAR")
  )
  (if (= nil (findfile DUALCARDCLNAME))
   (progn
    (setq DUALCARDCLNAME (vl-filename-mktemp "rfl.dcl"))
    (RFL:MAKEDCL DUALCARDCLNAME "DUALCAR")
   )
  )
 )
 (setq DCL_ID (load_dialog DUALCARDCLNAME))
 (if (not (new_dialog "DUALCAR" DCL_ID)) (exit))

 (INITIATE)
 (SETENABLED)

 (action_tile "LDF" "(set_tile \"LDV\" \"0\")(SETENABLED)")
 (action_tile "LDV" "(set_tile \"LDF\" \"0\")(SETENABLED)")
 (action_tile "MDF" "(set_tile \"MDV\" \"0\")(SETENABLED)")
 (action_tile "MDV" "(set_tile \"MDF\" \"0\")(SETENABLED)")
 (action_tile "RDF" "(set_tile \"RDV\" \"0\")(SETENABLED)")
 (action_tile "RDV" "(set_tile \"RDF\" \"0\")(SETENABLED)")
 (action_tile "LCOSF" "(set_tile \"LCOSV\" \"0\")(SETENABLED)")
 (action_tile "LCOSV" "(set_tile \"LCOSF\" \"0\")(SETENABLED)")
 (action_tile "RCOSF" "(set_tile \"RCOSV\" \"0\")(SETENABLED)")
 (action_tile "RCOSV" "(set_tile \"RCOSF\" \"0\")(SETENABLED)")
 (action_tile "LSOSF" "(set_tile \"LSOSV\" \"0\")(SETENABLED)")
 (action_tile "LSOSV" "(set_tile \"LSOSF\" \"0\")(SETENABLED)")
 (action_tile "RSOSF" "(set_tile \"RSOSV\" \"0\")(SETENABLED)")
 (action_tile "RSOSV" "(set_tile \"RSOSF\" \"0\")(SETENABLED)")
 (action_tile "LMOSF" "(set_tile \"LMOSV\" \"0\")(SETENABLED)")
 (action_tile "LMOSV" "(set_tile \"LMOSF\" \"0\")(SETENABLED)")
 (action_tile "RMOSF" "(set_tile \"RMOSV\" \"0\")(SETENABLED)")
 (action_tile "RMOSV" "(set_tile \"RMOSF\" \"0\")(SETENABLED)")
 (action_tile "LVF" "(SETENABLED)")
 (action_tile "LVV" "(SETENABLED)")
 (action_tile "RVF" "(SETENABLED)")
 (action_tile "RVV" "(SETENABLED)")
 (action_tile "FROMTOBEGIN" "(SETENABLED)")
 (action_tile "FROMTOEND" "(SETENABLED)")

 (action_tile "CHOR" "(CHECKFILE \"CHOR\" \".HOR\")")
 (action_tile "CVER" "(CHECKFILE \"CVER\" \".VRT\")")
 (action_tile "CSUPER" "(CHECKFILE \"CSUPER\" \".E\")")
 (action_tile "LDVVAL" "(CHECKFILE \"LDVVAL\" \".VRT\")")
 (action_tile "MDVVAL" "(CHECKFILE \"MDVVAL\" \".VRT\")")
 (action_tile "RDVVAL" "(CHECKFILE \"RDVVAL\" \".VRT\")")
 (action_tile "LCOSVVAL" "(CHECKFILE \"LCOSVVAL\" \".HOR\")")
 (action_tile "RCOSVVAL" "(CHECKFILE \"RCOSVVAL\" \".HOR\")")
 (action_tile "LSOSVVAL" "(CHECKFILE \"LSOSVVAL\" \".HOR\")")
 (action_tile "RSOSVVAL" "(CHECKFILE \"RSOSVVAL\" \".HOR\")")
 (action_tile "LMOSVVAL" "(CHECKFILE \"LMOSVVAL\" \".HOR\")")
 (action_tile "RMOSVVAL" "(CHECKFILE \"RMOSVVAL\" \".HOR\")")
 (action_tile "LVVVAL" "(CHECKFILE \"LVVVAL\" \".VRT\")")
 (action_tile "RVVVAL" "(CHECKFILE \"RVVVAL\" \".VRT\")")

 (action_tile "NORMAL" "(FIXNUMBER \"NORMAL\")")
 (action_tile "LDFVAL" "(FIXNUMBER \"LDFVAL\")")
 (action_tile "MDFVAL" "(FIXNUMBER \"MDFVAL\")")
 (action_tile "RDFVAL" "(FIXNUMBER \"RDFVAL\")")
 (action_tile "LSD1" "(FIXNUMBER \"LSD1\")")
 (action_tile "RSD1" "(FIXNUMBER \"RSD1\")")
 (action_tile "LSD2" "(FIXNUMBER \"LSD2\")")
 (action_tile "RSD2" "(FIXNUMBER \"RSD2\")")
 (action_tile "LCOSFVAL" "(FIXNUMBER \"LCOSFVAL\")")
 (action_tile "RCOSFVAL" "(FIXNUMBER \"RCOSFVAL\")")
 (action_tile "LSOSFVAL" "(FIXNUMBER \"LSOSFVAL\")")
 (action_tile "RSOSFVAL" "(FIXNUMBER \"RSOSFVAL\")")
 (action_tile "LMOSFVAL" "(FIXNUMBER \"LMOSFVAL\")")
 (action_tile "RMOSFVAL" "(FIXNUMBER \"RMOSFVAL\")")
 (action_tile "LSLOPE1" "(FIXNUMBER \"LSLOPE1\")")
 (action_tile "RSLOPE1" "(FIXNUMBER \"RSLOPE1\")")
 (action_tile "LSLOPE2" "(FIXNUMBER \"LSLOPE2\")")
 (action_tile "RSLOPE2" "(FIXNUMBER \"RSLOPE2\")")
 (action_tile "LSLOPE3" "(FIXNUMBER \"LSLOPE3\")")
 (action_tile "RSLOPE3" "(FIXNUMBER \"RSLOPE3\")")
 (action_tile "LSLOPE4" "(FIXNUMBER \"LSLOPE4\")")
 (action_tile "RSLOPE4" "(FIXNUMBER \"RSLOPE4\")")
 (action_tile "LSLOPE5" "(FIXNUMBER \"LSLOPE5\")")
 (action_tile "RSLOPE5" "(FIXNUMBER \"RSLOPE5\")")
 (action_tile "LSLOPE6" "(FIXNUMBER \"LSLOPE6\")")
 (action_tile "RSLOPE6" "(FIXNUMBER \"RSLOPE6\")")
 (action_tile "FROMTOSTARTVAL" "(FIXNUMBER \"FROMTOSTARTVAL\")")
 (action_tile "FROMTOENDVAL" "(FIXNUMBER \"FROMTOENDVAL\")")
 (action_tile "FROMTOSTEP" "(FIXNUMBER \"FROMTOSTEP\")")

 (action_tile "CHORPICK" "(PICKFILE \"CHOR\" \".HOR\")")
 (action_tile "CVERPICK" "(PICKFILE \"CVER\" \".VRT\")")
 (action_tile "LDVPICK" "(PICKFILE \"LDVVAL\" \".VRT\")")
 (action_tile "MDVPICK" "(PICKFILE \"MDVVAL\" \".VRT\")")
 (action_tile "RDVPICK" "(PICKFILE \"RDVVAL\" \".VRT\")")
 (action_tile "CSUPERPICK" "(PICKFILE \"CSUPER\" \".E\")")
 (action_tile "LCOSVPICK" "(PICKFILE \"LCOSVVAL\" \".HOR\")")
 (action_tile "RCOSVPICK" "(PICKFILE \"RCOSVVAL\" \".HOR\")")
 (action_tile "LSOSVPICK" "(PICKFILE \"LSOSVVAL\" \".HOR\")")
 (action_tile "RSOSVPICK" "(PICKFILE \"RSOSVVAL\" \".HOR\")")
 (action_tile "LMOSVPICK" "(PICKFILE \"LMOSVVAL\" \".HOR\")")
 (action_tile "RMOSVPICK" "(PICKFILE \"RMOSVVAL\" \".HOR\")")
 (action_tile "LVVPICK" "(PICKFILE \"LVVVAL\" \".VRT\")")
 (action_tile "RVVPICK" "(PICKFILE \"RVVVAL\" \".VRT\")")

 (action_tile "SSW" "(WRITESETTINGS)")
 (action_tile "SSR" "(READSETTINGS)")

 (action_tile "OK" "(ACCEPTDUALCAR)")
 (action_tile "CANCEL" "(CANCELDUALCAR)")

 (start_dialog)

 (if (= CANCEL 0)
  (progn
   (princ "\nChecking for input errors :\n")
   (if (= "n/a" (cdr (assoc "CHOR" RFL:DUALCARLIST)))
    (progn
     (princ "     *****     Centerline horizontal control not set!\n")
     (setq CANCEL 1)
    )
   )
   (if (= "n/a" (cdr (assoc "CVER" RFL:DUALCARLIST)))
    (progn
     (princ "     *****     Centerline vertical control not set!\n")
     (setq CANCEL 1)
    )
   )
   (if (= "n/a" (cdr (assoc "CSUPER" RFL:DUALCARLIST)))
    (progn
     (princ "     *****     Centerline superelevation control not set!\n")
     (setq CANCEL 1)
    )
   )
   (if (and (= "1" (cdr (assoc "LDV" RFL:DUALCARLIST))) (= "n/a" (cdr (assoc "LDVVAL" RFL:DUALCARLIST))))
    (progn
     (princ "     *****     Variable left ditch selected but not set!\n")
     (setq CANCEL 1)
    )
   )
   (if (and (= "1" (cdr (assoc "MDV" RFL:DUALCARLIST))) (= "n/a" (cdr (assoc "MDVVAL" RFL:DUALCARLIST))))
    (progn
     (princ "     *****     Variable median ditch selected but not set!\n")
     (setq CANCEL 1)
    )
   )
   (if (and (= "1" (cdr (assoc "RDV" RFL:DUALCARLIST))) (= "n/a" (cdr (assoc "RDVVAL" RFL:DUALCARLIST))))
    (progn
     (princ "     *****     Variable right ditch selected but not set!\n")
     (setq CANCEL 1)
    )
   )
   (if (and (= "1" (cdr (assoc "LCOSV" RFL:DUALCARLIST))) (= "n/a" (cdr (assoc "LCOSVVAL" RFL:DUALCARLIST))))
    (progn
     (princ "     *****     Variable left carriage centerline selected but not set!\n")
     (setq CANCEL 1)
    )
   )
   (if (and (= "1" (cdr (assoc "LSOSV" RFL:DUALCARLIST))) (= "n/a" (cdr (assoc "LSOSVVAL" RFL:DUALCARLIST))))
    (progn
     (princ "     *****     Variable left carriage shoulder selected but not set!\n")
     (setq CANCEL 1)
    )
   )
   (if (and (= "1" (cdr (assoc "LMOSV" RFL:DUALCARLIST))) (= "n/a" (cdr (assoc "LMOSVVAL" RFL:DUALCARLIST))))
    (progn
     (princ "     *****     Variable left carriage median selected but not set!\n")
     (setq CANCEL 1)
    )
   )
   (if (and (= "1" (cdr (assoc "RCOSV" RFL:DUALCARLIST))) (= "n/a" (cdr (assoc "RCOSVVAL" RFL:DUALCARLIST))))
    (progn
     (princ "     *****     Variable right carriage centerline selected but not set!\n")
     (setq CANCEL 1)
    )
   )
   (if (and (= "1" (cdr (assoc "RSOSV" RFL:DUALCARLIST))) (= "n/a" (cdr (assoc "RSOSVVAL" RFL:DUALCARLIST))))
    (progn
     (princ "     *****     Variable right carriage shoulder selected but not set!\n")
     (setq CANCEL 1)
    )
   )
   (if (and (= "1" (cdr (assoc "RMOSV" RFL:DUALCARLIST))) (= "n/a" (cdr (assoc "RMOSVVAL" RFL:DUALCARLIST))))
    (progn
     (princ "     *****     Variable right carriage median selected but not set!\n")
     (setq CANCEL 1)
    )
   )
   (if (and (= "1" (cdr (assoc "LVV" RFL:DUALCARLIST))) (= "n/a" (cdr (assoc "LVVVAL" RFL:DUALCARLIST))))
    (progn
     (princ "     *****     Independant left carriage profile selected but not set!\n")
     (setq CANCEL 1)
    )
   )
   (if (and (= "1" (cdr (assoc "RVV" RFL:DUALCARLIST))) (= "n/a" (cdr (assoc "RVVVAL" RFL:DUALCARLIST))))
    (progn
     (princ "     *****     Independant right carriage profile selected but not set!\n")
     (setq CANCEL 1)
    )
   )
   (if (= CANCEL 0)
    (progn
     (setq ALSAVE RFL:ALIGNLIST PVISAVE RFL:PVILIST SUPERSAVE RFL:SUPERLIST)

     (if (= "1" (cdr (assoc "LDV" RFL:DUALCARLIST)))
      (progn
       (RFL:RPROF (cdr (assoc "LDVVAL" RFL:DUALCARLIST)))
       (setq DITCHLEFT RFL:PVILIST)
      )
      (setq DITCHLEFT nil)
     )

     (if (= "1" (cdr (assoc "MDV" RFL:DUALCARLIST)))
      (progn
       (RFL:RPROF (cdr (assoc "MDVVAL" RFL:DUALCARLIST)))
       (setq DITCHMEDIAN RFL:PVILIST)
      )
      (setq DITCHMEDIAN nil)
     )

     (if (= "1" (cdr (assoc "RDV" RFL:DUALCARLIST)))
      (progn
       (RFL:RPROF (cdr (assoc "RDVVAL" RFL:DUALCARLIST)))
       (setq DITCHRIGHT RFL:PVILIST)
      )
      (setq DITCHRIGHT nil)
     )

     (if (= "1" (cdr (assoc "LCOSV" RFL:DUALCARLIST)))
      (progn
       (RFL:RALIGN (cdr (assoc "LCOSVVAL" RFL:DUALCARLIST)))
       (setq ALLEFT RFL:ALIGNLIST)
      )
      (setq ALLEFT nil)
     )

     (if (= "1" (cdr (assoc "LSOSV" RFL:DUALCARLIST)))
      (progn
       (RFL:RALIGN (cdr (assoc "LSOSVVAL" RFL:DUALCARLIST)))
       (setq ALLEFTSHLDR RFL:ALIGNLIST)
      )
      (setq ALLEFTSHLDR nil)
     )

     (if (= "1" (cdr (assoc "LMOSV" RFL:DUALCARLIST)))
      (progn
       (RFL:RALIGN (cdr (assoc "LMOSVVAL" RFL:DUALCARLIST)))
       (setq ALLEFTMDN RFL:ALIGNLIST)
      )
      (setq ALLEFTMDN nil)
     )

     (if (= "1" (cdr (assoc "RCOSV" RFL:DUALCARLIST)))
      (progn
       (RFL:RALIGN (cdr (assoc "RCOSVVAL" RFL:DUALCARLIST)))
       (setq ALRIGHT RFL:ALIGNLIST)
      )
      (setq ALRIGHT nil)
     )

     (if (= "1" (cdr (assoc "RSOSV" RFL:DUALCARLIST)))
      (progn
       (RFL:RALIGN (cdr (assoc "RSOSVVAL" RFL:DUALCARLIST)))
       (setq ALRIGHTSHLDR RFL:ALIGNLIST)
      )
      (setq ALRIGHTSHLDR nil)
     )

     (if (= "1" (cdr (assoc "RMOSV" RFL:DUALCARLIST)))
      (progn
       (RFL:RALIGN (cdr (assoc "RMOSVVAL" RFL:DUALCARLIST)))
       (setq ALRIGHTMDN RFL:ALIGNLIST)
      )
      (setq ALRIGHTMDN nil)
     )

     (if (= "1" (cdr (assoc "LVV" RFL:DUALCARLIST)))
      (progn
       (RFL:RPROF (cdr (assoc "LVVVAL" RFL:DUALCARLIST)))
       (setq LEFTPROF RFL:PVILIST)
      )
      (setq LEFTPROF nil)
     )

     (if (= "1" (cdr (assoc "RVV" RFL:DUALCARLIST)))
      (progn
       (RFL:RPROF (cdr (assoc "RVVVAL" RFL:DUALCARLIST)))
       (setq RIGHTPROF RFL:PVILIST)
      )
      (setq RIGHTPROF nil)
     )

     (RFL:RALIGN (cdr (assoc "CHOR" RFL:DUALCARLIST)))
     (setq CHOR RFL:ALIGNLIST)
     (RFL:RPROF (cdr (assoc "CVER" RFL:DUALCARLIST)))
     (setq CVER RFL:PVILIST)
     (RFL:RSUPER (cdr (assoc "CSUPER" RFL:DUALCARLIST)))
     (if (or (= nil RFL:ALIGNLIST) (= nil RFL:PVILIST) (= nil RFL:SUPERLIST))
      (princ "\n***** Problem reading centerline control!\n")
      (progn
       (if (= "1" (cdr (assoc "FROMTOBEGIN" RFL:DUALCARLIST)))
        (setq STASTART (max (caar RFL:ALIGNLIST)
			    (caar RFL:PVILIST)
			    (caar RFL:SUPERLIST)
		       )
	)
        (setq STASTART (cdr (assoc "FROMTOSTARTVAL" RFL:DUALCARLIST)))
       )
       (setq STA STASTART)
       (if (= "1" (cdr (assoc "FROMTOEND" RFL:DUALCARLIST)))
        (setq STAEND (min (+ (caar RFL:ALIGNLIST) (RFL:GETALIGNLENGTH))
			  (car (last RFL:PVILIST))
			  (car (last RFL:SUPERLIST))
		     )
	)
        (setq STAEND (cdr (assoc "FROMTOENDVAL" RFL:DUALCARLIST)))
       )
       (setq STASTEP (cdr (assoc "FROMTOSTEP" RFL:DUALCARLIST)))

       (princ "\n")

       (princ "\nCalculating points :\n")

       (setq STOPFLAG 0)

       (while (= STOPFLAG 0)
        (if (>= STA STAEND) (setq STOPFLAG 1))

        (princ (strcat "   " (rtos STA 2 0)))
        (PINWHEEL)

        (if (and (/= nil (RFL:SUPER STA))
                 (/= nil (RFL:ELEVATION STA))
                 (/= nil (RFL:XY (list STA 0.0))))
         (progn

          (setq SUPERLEFT (car (RFL:SUPER STA)))
          (setq SUPERRIGHT (cadr (RFL:SUPER STA)))

          (setq PL1 nil PL2 nil PL3 nil PL4 nil PL5 nil PL6 nil PL7 nil PL8 nil PL9 nil PL10 nil PL11 nil PL12 nil)

          (if (= nil LEFTPROF)
           (setq LELEV (RFL:ELEVATION STA))
           (progn
            (setq RFL:PVILIST LEFTPROF)
            (setq LELEV (RFL:ELEVATION STA))
            (setq RFL:PVILIST CVER)
           )
          )

          (if (= "1" (cdr (assoc "LCOSF" RFL:DUALCARLIST)))
           (setq LOS1 (cdr (assoc "LCOSFVAL" RFL:DUALCARLIST)))
           (setq LOS1 (* -1.0 (GETOFFSET STA 0.0 ALLEFT)))
          )
          (if (= "1" (cdr (assoc "LSOSF" RFL:DUALCARLIST)))
           (setq LSHLDR (cdr (assoc "LSOSFVAL" RFL:DUALCARLIST)))
           (setq LSHLDR (* -1.0 (GETOFFSET STA (* -1.0 LOS1) ALLEFTSHLDR)))
          )
          (if (= "1" (cdr (assoc "LMOSF" RFL:DUALCARLIST)))
           (setq LMDN (cdr (assoc "LMOSFVAL" RFL:DUALCARLIST)))
           (setq LMDN (GETOFFSET STA (* -1.0 LOS1) ALLEFTMDN))
          )
          (cond ((= "1" (cdr (assoc "LPIVOT4" RFL:DUALCARLIST)))
                 (progn
                  (setq PL4 (list (- LMDN LOS1) LELEV))
                  (setq PL5 (list (* -1.0 LOS1) (- LELEV (* SUPERRIGHT 0.01 LMDN))))
                  (setq PL6 (list (* -1.0 (+ LSHLDR LOS1)) (+ (cadr PL5) (* SUPERLEFT 0.01 LSHLDR))))
                 )
                )
                ((= "1" (cdr (assoc "LPIVOT5" RFL:DUALCARLIST)))
                 (progn
                  (setq PL5 (list (* -1.0 LOS1) LELEV))
                  (setq PL4 (list (- LMDN LOS1) (+ LELEV (* SUPERRIGHT 0.01 LMDN))))
                  (setq PL6 (list (* -1.0 (+ LSHLDR LOS1)) (+ LELEV (* SUPERLEFT 0.01 LSHLDR))))
                 )
                )
                ((= "1" (cdr (assoc "LPIVOT6" RFL:DUALCARLIST)))
                 (progn
                  (setq PL6 (list (* -1.0 (+ LSHLDR LOS1)) LELEV))
                  (setq PL5 (list (* -1.0 LOS1) (- LELEV (* SUPERLEFT 0.01 LSHLDR))))
                  (setq PL4 (list (- LMDN LOS1) (+ (cadr PL5) (* SUPERRIGHT 0.01 LMDN))))
                 )
                )
          )
          (setq D (cdr (assoc "LSD1" RFL:DUALCARLIST)))
          (setq PL11 (list (car PL5) (- (cadr PL5) D)))
          (setq SLOPE (cdr (assoc "LSLOPE3" RFL:DUALCARLIST)))
          (setq TMP (/ (* D SLOPE)
                       (+ 1.0 (* SLOPE (* 0.01 SUPERRIGHT)))
                    )
          )
          (setq PL3 (list (+ (car PL4) TMP)
                          (- (cadr PL4) D (* -1.0 TMP (* 0.01 SUPERRIGHT)))
                    )
          )
          (setq SLOPE (cdr (assoc "LSLOPE4" RFL:DUALCARLIST)))
          (setq TMP (/ (* D SLOPE)
                       (+ 1.0 (* SLOPE (* 0.01 SUPERLEFT)))
                    )
          )
          (setq PL7 (list (- (car PL6) TMP)
                          (- (cadr PL6) D (* -1.0 TMP (* 0.01 SUPERLEFT)))
                    )
          )

          (setq D (cdr (assoc "LSD2" RFL:DUALCARLIST)))
          (setq PL12 (list (car PL11) (- (cadr PL11) D)))
          (setq SLOPE (cdr (assoc "LSLOPE2" RFL:DUALCARLIST)))
          (setq TMP (/ (* D SLOPE)
                       (+ 1.0 (* SLOPE (* 0.01 SUPERRIGHT)))
                    )
          )
          (setq PL2 (list (+ (car PL3) TMP)
                          (- (cadr PL3) D (* -1.0 TMP (* 0.01 SUPERRIGHT)))
                    )
          )
          (setq SLOPE (cdr (assoc "LSLOPE5" RFL:DUALCARLIST)))
          (setq TMP (/ (* D SLOPE)
                       (+ 1.0 (* SLOPE (* 0.01 SUPERLEFT)))
                    )
          )
          (setq PL8 (list (- (car PL7) TMP)
                          (- (cadr PL7) D (* -1.0 TMP (* 0.01 SUPERLEFT)))
                    )
          )

          (if (= nil DITCHLEFT)
           (setq TMP (- (cadr PL8) (cdr (assoc "LDFVAL" RFL:DUALCARLIST))))
           (progn
            (setq RFL:PVILIST DITCHLEFT)
            (setq TMP (RFL:ELEVATION STA))
            (setq RFL:PVILIST CVER)
           )
          )
          (setq PL9 (list (- (car PL8)
                             (* (cdr (assoc "LSLOPE6" RFL:DUALCARLIST))
                                (- (cadr PL8) TMP)
                             )
                          )
                          TMP
                    )
          )
          (setq PL10 (list (- (car PL9) (cdr (assoc "LDW" RFL:DUALCARLIST)))
                           TMP
                     )
          )

          (if (= nil DITCHMEDIAN)
           (setq TMP (- (RFL:ELEVATION STA) (cdr (assoc "MDFVAL" RFL:DUALCARLIST))))
           (progn
            (setq RFL:PVILIST DITCHMEDIAN)
            (setq TMP (RFL:ELEVATION STA))
            (setq RFL:PVILIST CVER)
           )
          )
          (setq PL1 (list (+ (car PL2)
                             (* (cdr (assoc "LSLOPE1" RFL:DUALCARLIST))
                                (- (cadr PL2) TMP)
                             )
                          )
                          TMP
                    )
          )

          (setq PR1 nil PR2 nil PR3 nil PR4 nil PR5 nil PR6 nil PR7 nil PR8 nil PR9 nil PR10 nil PR11 nil PR12 nil)

          (if (= nil RIGHTPROF)
           (setq RELEV (RFL:ELEVATION STA))
           (progn
            (setq RFL:PVILIST RIGHTPROF)
            (setq RELEV (RFL:ELEVATION STA))
            (setq RFL:PVILIST CVER)
           )
          )

          (if (= "1" (cdr (assoc "RCOSF" RFL:DUALCARLIST)))
           (setq ROS1 (cdr (assoc "RCOSFVAL" RFL:DUALCARLIST)))
           (setq ROS1 (GETOFFSET STA 0.0 ALRIGHT))
          )
          (if (= "1" (cdr (assoc "RSOSF" RFL:DUALCARLIST)))
           (setq RSHLDR (cdr (assoc "RSOSFVAL" RFL:DUALCARLIST)))
           (setq RSHLDR (GETOFFSET STA ROS1 ALRIGHTSHLDR))
          )
          (if (= "1" (cdr (assoc "RMOSF" RFL:DUALCARLIST)))
           (setq RMDN (cdr (assoc "RMOSFVAL" RFL:DUALCARLIST)))
           (setq RMDN (* -1.0 (GETOFFSET STA ROS1 ALRIGHTMDN)))
          )
          (cond ((= "1" (cdr (assoc "RPIVOT4" RFL:DUALCARLIST)))
                 (progn
                  (setq PR4 (list (- ROS1 RMDN) RELEV))
                  (setq PR5 (list ROS1 (- RELEV (* SUPERLEFT 0.01 RMDN))))
                  (setq PR6 (list (+ RSHLDR ROS1) (+ (cadr PR5) (* SUPERRIGHT 0.01 RSHLDR))))
                 )
                )
                ((= "1" (cdr (assoc "RPIVOT5" RFL:DUALCARLIST)))
                 (progn
                  (setq PR5 (list ROS1 RELEV))
                  (setq PR4 (list (- ROS1 RMDN) (+ RELEV (* SUPERLEFT 0.01 RMDN))))
                  (setq PR6 (list (+ RSHLDR ROS1) (+ RELEV (* SUPERRIGHT 0.01 RSHLDR))))
                 )
                )
                ((= "1" (cdr (assoc "RPIVOT6" RFL:DUALCARLIST)))
                 (progn
                  (setq PR6 (list (+ RSHLDR ROS1) RELEV))
                  (setq PR5 (list ROS1 (- RELEV (* SUPERRIGHT 0.01 RSHLDR))))
                  (setq PR4 (list (- ROS1 RMDN) (+ (cadr PR5) (* SUPERLEFT 0.01 RMDN))))
                 )
                )
          )
          (setq D (cdr (assoc "RSD1" RFL:DUALCARLIST)))
          (setq PR11 (list (car PR5) (- (cadr PR5) D)))
          (setq SLOPE (cdr (assoc "RSLOPE3" RFL:DUALCARLIST)))
          (setq TMP (/ (* D SLOPE)
                       (+ 1.0 (* SLOPE (* 0.01 SUPERLEFT)))
                    )
          )
          (setq PR3 (list (- (car PR4) TMP)
                          (- (cadr PR4) D (* -1.0 TMP (* 0.01 SUPERLEFT)))
                    )
          )
          (setq SLOPE (cdr (assoc "RSLOPE4" RFL:DUALCARLIST)))
          (setq TMP (/ (* D SLOPE)
                       (+ 1.0 (* SLOPE (* 0.01 SUPERRIGHT)))
                    )
          )
          (setq PR7 (list (+ (car PR6) TMP)
                          (- (cadr PR6) D (* -1.0 TMP (* 0.01 SUPERRIGHT)))
                    )
          )

          (setq D (cdr (assoc "RSD2" RFL:DUALCARLIST)))
          (setq PR12 (list (car PR11) (- (cadr PR11) D)))
          (setq SLOPE (cdr (assoc "RSLOPE2" RFL:DUALCARLIST)))
          (setq TMP (/ (* D SLOPE)
                       (+ 1.0 (* SLOPE (* 0.01 SUPERLEFT)))
                    )
          )
          (setq PR2 (list (- (car PR3) TMP)
                          (- (cadr PR3) D (* -1.0 TMP (* 0.01 SUPERLEFT)))
                    )
          )
          (setq SLOPE (cdr (assoc "RSLOPE5" RFL:DUALCARLIST)))
          (setq TMP (/ (* D SLOPE)
                       (+ 1.0 (* SLOPE (* 0.01 SUPERRIGHT)))
                    )
          )
          (setq PR8 (list (+ (car PR7) TMP)
                          (- (cadr PR7) D (* -1.0 TMP (* 0.01 SUPERRIGHT)))
                    )
          )

          (if (= nil DITCHRIGHTT)
           (setq TMP (- (cadr PR8) (cdr (assoc "RDFVAL" RFL:DUALCARLIST))))
           (progn
            (setq RFL:PVILIST DITCHRIGHTT)
            (setq TMP (RFL:ELEVATION STA))
            (setq RFL:PVILIST CVER)
           )
          )
          (setq PR9 (list (+ (car PR8)
                             (* (cdr (assoc "RSLOPE6" RFL:DUALCARLIST))
                                (- (cadr PR8) TMP)
                             )
                          )
                          TMP
                    )
          )
          (setq PR10 (list (+ (car PR9) (cdr (assoc "RDW" RFL:DUALCARLIST)))
                           TMP
                     )
          )

          (if (= nil DITCHMEDIAN)
           (setq TMP (- (RFL:ELEVATION STA) (cdr (assoc "MDFVAL" RFL:DUALCARLIST))))
           (progn
            (setq RFL:PVILIST DITCHMEDIAN)
            (setq TMP (RFL:ELEVATION STA))
            (setq RFL:PVILIST CVER)
           )
          )
          (setq PR1 (list (- (car PR2)
                             (* (cdr (assoc "RSLOPE1" RFL:DUALCARLIST))
                                (- (cadr PR2) TMP)
                             )
                          )
                          TMP
                    )
          )

          (setq DUALCARSECTIONLIST
                (append DUALCARSECTIONLIST
                        (list (list STA
                                    (cons "PL1" PL1)
                                    (cons "PL2" PL2)
                                    (cons "PL3" PL3)
                                    (cons "PL4" PL4)
                                    (cons "PL5" PL5)
                                    (cons "PL6" PL6)
                                    (cons "PL7" PL7)
                                    (cons "PL8" PL8)
                                    (cons "PL9" PL9)
                                    (cons "PL10" PL10)
                                    (cons "PL11" PL11)
                                    (cons "PL12" PL12)
                                    (cons "PR1" PR1)
                                    (cons "PR2" PR2)
                                    (cons "PR3" PR3)
                                    (cons "PR4" PR4)
                                    (cons "PR5" PR5)
                                    (cons "PR6" PR6)
                                    (cons "PR7" PR7)
                                    (cons "PR8" PR8)
                                    (cons "PR9" PR9)
                                    (cons "PR10" PR10)
                                    (cons "PR11" PR11)
                                    (cons "PR12" PR12)
                              )
                        )
                )
          )

         )
        )

        (setq STA (- (+ STA STASTEP) (rem STA STASTEP)))
        (if (>= STA STAEND) (setq STA STAEND))

       )
       (princ "\nDrawing 3D-Polylines :\n")
       (setq LR 0)
       (while (< LR 2)
        (setq CP 1)
        (while (< CP 13)
         (if (= LR 0)
          (setq CODE (strcat "L" (itoa CP)))
          (setq CODE (strcat "R" (itoa CP)))
         )
         (if (= "1" (cdr (assoc (strcat "D" CODE) RFL:DUALCARLIST)))
          (progn
           (princ (strcat "Drawing : " CODE "\n"))
           (setq STARTFLAG 1)
           (command "._3DPOLY")
           (setq C 0)
           (while (< C (length DUALCARSECTIONLIST))
            (setq NODE (nth C DUALCARSECTIONLIST))
            (setq STA (car NODE))
            (setq TMP (cdr (assoc (strcat "P" CODE) (cdr NODE))))
            (if (/= nil TMP)
             (progn
              (setq OFFSET (car TMP))
              (setq ELEV (cadr TMP))
              (setq P (RFL:XY (list STA OFFSET)))
              (command (list (nth 0 P) (nth 1 P) ELEV))
             )
            )
            (setq C (+ C 1))
           )
           (command "")
          )
         )
         (setq CP (+ CP 1))
        )
        (setq LR (+ LR 1))
       )

       (if (= "1" (cdr (assoc "FROMTOFILE" RFL:DUALCARLIST)))
        (progn
         (setq OUTFILE (getfiled "Select a file for saving" (vl-registry-read "HKEY_CURRENT_USER\\rflAlignDirectory") "" 1))
         (if (/= nil OUTFILE)
          (progn
           (setq OUTFILE (open OUTFILE "w"))
           (setq C 0)
           (while (< C (length DUALCARSECTIONLIST))
            (setq NODE (nth C DUALCARSECTIONLIST))
            (princ (rtos (car NODE) 2 8) OUTFILE)
            (princ "," OUTFILE)
            (setq NODE (cdr NODE))
            (if (= "1" (cdr (assoc "DL1" RFL:DUALCARLIST)))
             (progn
              (princ "L1," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL2" RFL:DUALCARLIST)))
             (progn
              (princ "L2," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL3" RFL:DUALCARLIST)))
             (progn
              (princ "L3," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL4" RFL:DUALCARLIST)))
             (progn
              (princ "L4," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL5" RFL:DUALCARLIST)))
             (progn
              (princ "L5," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL6" RFL:DUALCARLIST)))
             (progn
              (princ "L6," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL7" RFL:DUALCARLIST)))
             (progn
              (princ "L7," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL8" RFL:DUALCARLIST)))
             (progn
              (princ "L8," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL9" RFL:DUALCARLIST)))
             (progn
              (princ "L9," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL10" RFL:DUALCARLIST)))
             (progn
              (princ "L10," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL11" RFL:DUALCARLIST)))
             (progn
              (princ "L11," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DL12" RFL:DUALCARLIST)))
             (progn
              (princ "L12," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR1" RFL:DUALCARLIST)))
             (progn
              (princ "R1," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR2" RFL:DUALCARLIST)))
             (progn
              (princ "R2," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR3" RFL:DUALCARLIST)))
             (progn
              (princ "R3," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR4" RFL:DUALCARLIST)))
             (progn
              (princ "R4," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR5" RFL:DUALCARLIST)))
             (progn
              (princ "R5," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR6" RFL:DUALCARLIST)))
             (progn
              (princ "R6," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR7" RFL:DUALCARLIST)))
             (progn
              (princ "R7," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR8" RFL:DUALCARLIST)))
             (progn
              (princ "R8," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR9" RFL:DUALCARLIST)))
             (progn
              (princ "R9," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR10" RFL:DUALCARLIST)))
             (progn
              (princ "R10," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR11" RFL:DUALCARLIST)))
             (progn
              (princ "R11," OUTFILE)
              (princ (rtos (nth 1 (car NODE)) 2 8) OUTFILE)
              (princ "," OUTFILE)
              (princ (rtos (nth 2 (car NODE)) 2 8) OUTFILE)
              (princ "," OUTFILE)
             )
            )
            (setq NODE (cdr NODE))
            (if (= "1" (cdr (assoc "DR12" RFL:DUALCARLIST)))
             (progn
              (princ "R12," OUTFILE)
              (princ (rtos (nth 1 (car NODE)) 2 8) OUTFILE)
              (princ "," OUTFILE)
              (princ (rtos (nth 2 (car NODE)) 2 8) OUTFILE)
              (princ "," OUTFILE)
             )
            )
            (princ "\n" OUTFILE)
            (setq C (+ C 1))
           )
           (close OUTFILE)
          )
         )
        )
       )
      )
     )
    )
   )
  )
 )

 (setvar "CMDECHO" CMDECHO)
 (setvar "ORTHOMODE" ORTHOMODE)
 (setvar "OSMODE" OSMODE)
)
