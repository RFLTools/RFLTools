;
;
;     Program written by Robert Livingston, 2021-08-10
;
;     ROTATE2PL is a utility for rotating signs to be aligned with roadway polylines
;
;
(defun C:ROTATE2PL ( / ANG C ENT ENTLIST P1 P2 REP RFL:ALIGNLIST SIGNENT SIGNENTLIST SIGNENTSET TEMPENT ZOOMTO)
 (defun ZOOMTO (ENT / ENTLIST P Z)
  (setq Z 25.0)
  (setq ENTLIST (entget ENT))
  (setq P (cdr (assoc 10 ENTLIST)))
  (command-s "._ZOOM" "W" "NON" (list (- (car P) Z) (- (cadr P) Z)) "NON" (list (+ (car P) Z) (+ (cadr P) Z)))
 )
 (command-s "._UNDO" "M")
 (if (setq ENT (car (entsel "\nSelect sign entity (program will select all similar) : ")))
  (if (= (cdr (assoc 0 (setq ENTLIST (entget ENT)))) "INSERT")
   (progn
    (setq SIGNENTSET (ssget "X" (list (assoc 0 ENTLIST)
                                      (assoc 2 ENTLIST)
                                      (assoc 8 ENTLIST)
                                )
                     )
    )
;    Below is indended to sort the set so the selected entity is the first one:
;    (while (/= ENT (setq TEMPENT (ssname SIGNENTSET 0)))
;     (setq SIGNENTSET (ssadd TEMPENT (ssdel TEMPENT SIGNENTSET)))
;    )
    (setq C 0)
    (while (< C (sslength SIGNENTSET))
     (setq SIGNENT (ssname SIGNENTSET C))
     (setq SIGNENTLIST (entget SIGNENT))
     (setq P1 (cdr (assoc 10 SIGNENTLIST)))
     (setq P1 (list (car P1) (cadr P1)))
     (ZOOMTO SIGNENT)
     (redraw SIGNENT 3)
     (princ (strcat (itoa (1+ C)) " of " (itoa (sslength SIGNENTSET)) "\n"))
     (setq ENTLIST nil)
     (while (/= (cdr (assoc 0 ENTLIST)) "LWPOLYLINE") (setq ENTLIST (entget (setq ENT (car (entsel "\nSelect an lwpolyline for alignment : ")))))
      (if (/= (cdr (assoc 0 ENTLIST)) "LWPOLYLINE") 
       (princ "\nNot a polyline!")
       (progn
        (setq RFL:ALIGNLIST (RFL:ALIGNDEF ENT (cdr (assoc 10 ENTLIST)) 0.0))
        (if (not (RFL:STAOFF P1))
         (progn
          (princ "\nUnable to align sign to polyline - is the sign within the length of the polyline?")
          (setq ENTLIST nil)
         )
        )
       )
      )
     )
     (setq P2 (RFL:XY (list (car (RFL:STAOFF P1)) 0.0)))
     (setq ANG (+ (/ pi 2.0) (angle P1 P2)))
     (setq REP T)
     (while REP
      (princ "<R> to rotate, <N> for next, <P> for previous, <Q> to quit : ")
      (setq REP (grread))
      (cond ((or (= (cadr REP) 82) (= (cadr REP) 114))
             (progn
              (setq ANG (+ ANG (/ pi 2.0)))
              (entmod (subst (cons 50 ANG) (assoc 50 SIGNENTLIST) SIGNENTLIST))
              (redraw SIGNENT 3)
             )
            )
            ((or (= (cadr REP) 78) (= (cadr REP) 110))
             (setq C (1+ C) REP nil)
            )
            ((or (= (cadr REP) 80) (= (cadr REP) 112))
             (setq C (1- C) REP nil)
            )
            ((or (= (cadr REP) 81) (= (cadr REP) 113))
             (setq C (+ (sslength SIGNENTSET) 2) REP nil)
            )
      )
      (if (< C 0) (setq C 0))
      (if (= C (sslength SIGNENTSET)) (setq C (1- (sslength SIGNENTSET))))
     )
     (redraw SIGNENT 4)
    )
   )
   (princ "\nNot a block!")
  )
 )
 nil
)
