;
;
;     Program written by Robert Livingston, 2021-10-20
;
;     C:DRAWBARRIER is a utility for drawing/designing BC MoTI barriers.
;
;
(setq RFL:BARRIERLIST (list (cons "CBN-E" 1.2)          ; Precast Concrete Bull-Nose 460 mm
                            (cons "CBN-H" 1.2)          ; Precast Concrete Bull-Nose 460 mm
                            (cons "CRB-E" 2.5)          ; Precast Concrete Roadside Barrier 690 mm
                            (cons "CRB-H" 2.5)          ; Precast Concrete Roadside Barrier 690 mm
                            (cons "CDB-E" 2.5)          ; Precast Concrete Drainage Barrier 690 mm
                            (cons "CMB-E" 2.5)          ; Precast Concrete Median Barrier 810 mm
                            (cons "CMB-H" 2.5)          ; Precast Concrete Median Barrier 810 mm
                            (cons "CMDB-E" 2.5)         ; Precast Concrete Median Drainage Barrier 810 mm
                            (cons "CTB-1E" 2.5)         ; Precast Concrete Transition Barrier 690 mm to 460 mm
                            (cons "CTB-2H" 1.3)         ; Precast Concrete Transition Barrier 810 mm to 690 mm
                            (cons "CTB-3H" 2.5)         ; Precast Concrete Transition Barrier 686 mm to 690 mm
                            (cons "CTB-3E+H" 2.5)       ; Precast Concrete Transition Barrier 686 mm to 690 mm
                            (cons "SP941-03.04.01" 2.0) ; Standard Bridge Parapet Transition 810 mm
                      )
)
;(defun C:DRAWBARRIER (/ *error* ALSAVE ANGBASE ANGDIRCMDECHO D DIR DOS EH ENT ENTLIST FRATE GETENDPOINT GRADEAL GRADEFACTOR GRADEFLAG LASTPIECE N ORTHOMODE OS OS1 OS2 OSMODE P P1 P2 PLIST PREVENT REP REP2 RFL:ALIGNLIST RFL:PVILIST S S1 S2 SIDE SNAPANG TMP W)
(defun C:DRAWBARRIER ()
 (command "._UNDO" "M")
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setq ORTHOMODE (getvar "ORTHOMODE"))
 (setq SNAPANG (getvar "SNAPANG"))

 (defun *error* (msg)
  (setvar "CMDECHO" CMDECHO)
  (setvar "ANGBASE" ANGBASE)
  (setvar "ANGDIR" ANGDIR)
  (setvar "OSMODE" OSMODE)
  (setvar "ORTHOMODE" ORTHOMODE)
  (setvar "SNAPANG" SNAPANG)
  (princ msg)
 )
 
 (defun GRADEFACTOR (P / F G STA)
  (setq RFL:ALIGNLIST GRADEAL)
  (setq F 1.0)
  (if GRADEFLAG
   (progn
    (if (setq STA (car (RFL:STAOFF P)))
     (if (setq G (RFL:SLOPE STA))
      (setq F (sqrt (- 1.0 (* G G))))
      (princ "\n!!! Point not on profile !!!\n")
     )
     (princ "\n!!! Point not on alignment !!!\n")
    )
   )
  )
  (setq RFL:ALIGNLIST ALSAVE)
  F
 )
 
 (defun GETD (PIECE / D NODE)
  (setq D nil)
  (foreach NODE RFL:BARRIERLIST
   (if (vl-string-search PIECE (car NODE))
    (setq D (cdr NODE))
   )
  )
  D
 )
 
 (defun GETENDPOINT (P1 D OS2 / OS1 P P2 STA STA1 STA2)
  (setq OS2 (* SIDE OS2))
  (setq D (* DIR D))
  (setq OS1 (RFL:STAOFF P1))
  (setq STA1 (car OS1))
  (setq OS1 (cadr OS1))
  (setq STA2 STA1)
  (while (< (distance P1 (setq P2 (RFL:XY (list STA2 OS2)))) (abs D)) (setq STA2 (+ STA2 D)))
  (setq P (RFL:XY (list (setq STA (/ (+ STA1 STA2) 2.0)) OS2)))
  (while (> (abs (- (abs D) (distance P1 P))) RFL:TOL)
   (if (> (distance P1 P) (abs D))
    (setq STA2 STA)
    (setq STA1 STA)
   )
   (setq P (RFL:XY (list (setq STA (/ (+ STA1 STA2) 2.0)) OS2)))
  )
  P
 )
 
 (defun LABELBARRIER (P1 P2 LABEL H / P)
  (setq P (list (/ (+ (car P1) (car P2)) 2.0) (/ (+ (cadr P1) (cadr P2)) 2.0)))
  (entmake (list (cons 0 "TEXT")
                 (cons 1 LABEL)
                 (cons 7 "STANDARD")
                 (cons 8 (getvar "CLAYER"))
                 (cons 10 P)
                 (cons 11 P)
                 (cons 40 H)
                 (cons 50 (angle P (RFL:XY (list (car (RFL:STAOFF P)) 0.0))))
                 (cons 71 0)
                 (cons 72 1)
                 (cons 73 2)
           )
  )
 )
 
 (setq FRATE 0.0)
 (setq LASTPIECE nil)
 (setq EH nil)
 (if (not (setq W (getdist "\nEnter default barrier width <0.600> : "))) (setq W 0.6))
 (setq ENT (car (entsel "\nSelect EOL polyline for barrier control : ")))
 (setq ENTLIST (entget ENT))
 (if (= (cdr (assoc 0 ENTLIST)) "POLYLINE")
  (progn
   (command "._CONVERTPOLY" "L" ENT "")
   (setq ENTLIST (entget ENT))
  )
 )
 (if (= (cdr (assoc 0 ENTLIST)) "LWPOLYLINE")
  (progn
   (setq RFL:ALIGNLIST (RFL:ALIGNDEF ENT (cdr (assoc 10 ENTLIST)) 0.0))
   (setq ALSAVE RFL:ALIGNLIST)
   (setq P1 (getpoint "\nStart point of barrier : "))
   (if (setq S1 (RFL:STAOFF P1))
    (progn
     (setq SIDE (RFL:SIGN (cadr S1)))
     (if (setq OS1 (getdist (strcat "\nEnter offset to face of barrier <" (rtos (- (abs (cadr S1)) (/ W 2.0))) "> : ")))
      (setq OS1 (+ OS1 (/ W 2.0)))
      (setq OS1 (abs (cadr S1)))
     )
     (setq P1 (RFL:XY (list (car S1) (* OS1 SIDE))))
;     (initget "Eye Hook")
;     (if (not (setq EH (getkword "\nIs first barrier piece an Eye or a Hook (<Eye> / Hook) : "))) (setq EH "Eye"))
     (initget "CRB CMB")
     (setq LASTPIECE (getkword "\nConnecting barrier piece (<none> / CRB / CMB) : "))
     (initget "Eye Hook")
     (if (not (setq EH (getkword "\nIs first barrier piece an Eye or a Hook (<Eye> / Hook) : "))) (setq EH "Eye"))
     (setvar "SNAPANG" (angle (RFL:XY (list (car S1) 0.0)) (RFL:XY (list (car S1) 1.0))))
     (setvar "ORTHOMODE" 1)
     (setvar "OSMODE" 0)
     (setq P2 (getpoint P1 "\nDirection for barrier : "))
     (setvar "SNAPANG" SNAPANG)
     (setvar "ORTHOMODE" ORTHOMODE)
     (setvar "OSMODE" OSMODE)
     (princ "\nNote:  Adjusting for grade is a work in progress but may assist with long barrier runs.")
     (initget "Yes No")
     (if (= "Yes" (setq GRADEFLAG (getkword "\nAdjust lengths for grade (Yes/<No>) : ")))
      (progn
       (initget "C3D RFL")
       (if (setq REP (getkword "\nUse C3D or RFL for alignment/profile (<C3D>/RFL) : "))
        (C:RAB)
        (progn
         (setq OBALIGNMENT (RFL:GETC3DALIGNMENT))
         (RFL:RALIGNC3D OBALIGNMENT)
         (setq OBPROFILE (RFL:GETC3DPROFILE OBALIGNMENT))
         (RFL:RPROFC3D OBPROFILE)
        )
       )
       (setq GRADEAL RFL:ALIGNLIST)
       (setq RFL:ALIGNLIST ALSAVE)
      )
     )
     (if (setq S2 (RFL:STAOFF P2))
      (progn
       (setq DIR (RFL:SIGN (- (car S2) (car S1))))
       (setq REP "CRB")
       (while (/= REP "Stop")
        (initget "CRB CMB Transition Stop")
        (if (setq TMP (getkword (strcat "\nType of barrier to draw (CRB / CMB / Transition / Stop) <" REP "> : "))) (setq REP TMP))
        (setq PREVENT nil)
        (cond ((= REP "CRB")
               (progn
                (setq LASTPIECE "CRB")
;                (setq D 2.5)
                (setq D (GETD "CRB"))
                (setq N 0)
                (setq REP2 1)
                (while (< N 1)
                 (if (setq N (getint "\nEnter number of pieces (<return> to calculate based on distance) : "))
                  (if (< N 1) (princ "\nN must be greater than 1!"))
                  (if (setq REP2 (getdist P1 "\nDistance to end of barrier run : "))
                   (princ (strcat "\n" (rtos REP2) "m equates to " (rtos (/ REP2 2.5)) " 2.5m pieces."))
                  )
                 )
                )
;                (if (setq OS2 (getdist (strcat "\nEnter end offset to face of barrier <" (rtos (- OS1 (/ W 2.0))) "> : ")))
                (if (setq OS2 (getdist (strcat "\nEnter end offset to face of barrier <" (rtos (- (+ OS1 (* N D FRATE)) (/ W 2.0))) "> : ")))
                 (setq OS2 (+ OS2 (/ W 2.0)))
;                 (setq OS2 OS1)
                 (setq OS2 (+ OS1 (* N D FRATE)))
                )
                (setq FRATE (/ (- OS2 OS1) (* N D)))
                (setq OS OS1)
                (setq DOS (/ (- OS2 OS1) N))
                (setq PLIST (list P1))
                (while (> N 0)
                 (setq P2 (GETENDPOINT P1 (* D (GRADEFACTOR P1)) (setq OS (+ OS DOS))))
                 (setq PLIST (append PLIST (list P2)))
                 (LABELBARRIER P1 P2 (strcat "CRB-" (if (= EH "Eye") "E" "H")) (/ W 2.0))
                 (setq ENT (entlast))(RFL:PUTPREVENT ENT PREVENT)(RFL:PUTNEXTENT PREVENT ENT)(setq PREVENT ENT)
                 (if (= EH "Eye") (setq EH "Hook") (setq EH "Eye"))
                 (setq N (1- N))
                 (setq P1 P2)
                )
                (command "._PLINE")
                (foreach P PLIST
                 (progn
                  (command "_NON" P)
                 )
                )
                (command "")
                (setq ENT (entlast))(RFL:PUTPREVENT ENT PREVENT)(RFL:PUTNEXTENT PREVENT ENT)(setq PREVENT ENT)
                (setq OS1 OS)
               )
              )
              ((= REP "CMB")
               (progn
                (setq LASTPIECE "CMB")
;                (setq D 2.5)
                (setq D (GETD "CMB"))
                (setq N 0)
                (setq REP2 1)
                (while (< N 1)
                 (if (setq N (getint "\nEnter number of pieces (<return> to calculate based on distance) : "))
                  (if (< N 1) (princ "\nN must be greater than 1!"))
                  (if (setq REP2 (getdist P1 "\nDistance to end of barrier run : "))
                   (princ (strcat "\n" (rtos REP2) "m equates to " (rtos (/ REP2 2.5)) " 2.5m pieces."))
                  )
                 )
                )
;                (if (setq OS2 (getdist (strcat "\nEnter end offset to face of barrier <" (rtos (- OS1 (/ W 2.0))) "> : ")))
                (if (setq OS2 (getdist (strcat "\nEnter end offset to face of barrier <" (rtos (- (+ OS1 (* N D FRATE)) (/ W 2.0))) "> : ")))
                 (setq OS2 (+ OS2 (/ W 2.0)))
;                 (setq OS2 OS1)
                 (setq OS2 (+ OS1 (* N D FRATE)))
                )
                (setq FRATE (/ (- OS2 OS1) (* N D)))
                (setq OS OS1)
                (setq DOS (/ (- OS2 OS1) N))
                (setq PLIST (list P1))
                (while (> N 0)
                 (setq P2 (GETENDPOINT P1 (* D (GRADEFACTOR P1)) (setq OS (+ OS DOS))))
                 (setq PLIST (append PLIST (list P2)))
                 (LABELBARRIER P1 P2 (strcat "CMB-" (if (= EH "Eye") "E" "H")) (/ W 2.0))
                 (setq ENT (entlast))(RFL:PUTPREVENT ENT PREVENT)(RFL:PUTNEXTENT PREVENT ENT)(setq PREVENT ENT)
                 (if (= EH "Eye") (setq EH "Hook") (setq EH "Eye"))
                 (setq N (1- N))
                 (setq P1 P2)
                )
                (command "._PLINE")
                (foreach P PLIST
                 (progn
                  (command "_NON" P)
                 )
                )
                (command "")
                (setq ENT (entlast))(RFL:PUTPREVENT ENT PREVENT)(RFL:PUTNEXTENT PREVENT ENT)(setq PREVENT ENT)
                (setq OS1 OS)
               )
              )
              ((= REP "Transition")
               (progn
                (setq REP 0)
                (while (or (< REP 1) (> REP 3))
                 (princ "\n1 : Nose")
                 (princ "\n2 : Transition Barrier 810 mm to 690 mm")
                 (princ "\n3 : Bridge Parapet Transition 810 mm")
                 (setq REP (getint "\n     Transition type (1 to 3) <1> : "))
                 (if (= nil REP) (setq REP 1))
                 (if (or (< REP 1) (> REP 3)) (princ "\nPlease enter 1 to 3!"))
                )
                (cond ((= REP 1)
                       (cond ((or (= LASTPIECE "CRB") (= LASTPIECE nil))
                              (if (= EH "Eye")
                               (progn
                                (setq PLIST (list P1))
;                                (setq D 2.5)
                                (setq D (GETD "CTB-1E"))
                                (setq OS2 (+ OS1 (* D FRATE)))
                                (setq P2 (GETENDPOINT P1 (* D (GRADEFACTOR P1)) OS2))
                                (setq PLIST (append PLIST (list P2)))
                                (LABELBARRIER P1 P2 "CTB-1E" (/ W 2.0))
                                (setq ENT (entlast))(RFL:PUTPREVENT ENT PREVENT)(RFL:PUTNEXTENT PREVENT ENT)(setq PREVENT ENT)
                                (setq P1 P2)
                                (setq OS1 OS2)
;                                (setq D 1.2)
                                (setq D (GETD "CBN-H"))
                                (setq OS2 (+ OS1 (* D FRATE)))
                                (setq P2 (GETENDPOINT P1 (* D (GRADEFACTOR P1)) OS2))
                                (setq PLIST (append PLIST (list P2)))
                                (LABELBARRIER P1 P2 "CBN-H" (/ W 2.0))
                                (setq ENT (entlast))(RFL:PUTPREVENT ENT PREVENT)(RFL:PUTNEXTENT PREVENT ENT)(setq PREVENT ENT)
                                (command "._PLINE")
                                (foreach P PLIST
                                 (progn
                                  (command "_NON" P)
                                 )
                                )
                                (command "")
                                (setq ENT (entlast))(RFL:PUTPREVENT ENT PREVENT)(RFL:PUTNEXTENT PREVENT ENT)(setq PREVENT ENT)
                                (setq REP "Stop")
                               )
                               (progn
                                (princ "\nCannot place nose!  Previous barrier needs to be CRB-H.")
                                (setq REP "CRB")
                               )
                              )
                             )
                             ((or (= LASTPIECE "CMB") (= LASTPIECE nil))
                              (if (= EH "Hook")
                               (progn
                                (setq PLIST (list P1))
;                                (setq D 1.3)
                                (setq D (GETD "CTB-2H"))
                                (setq OS2 (+ OS1 (* D FRATE)))
                                (setq P2 (GETENDPOINT P1 (* D (GRADEFACTOR P1)) OS2))
                                (setq PLIST (append PLIST (list P2)))
                                (LABELBARRIER P1 P2 "CTB-2H" (/ W 2.0))
                                (setq ENT (entlast))(RFL:PUTPREVENT ENT PREVENT)(RFL:PUTNEXTENT PREVENT ENT)(setq PREVENT ENT)
                                (setq P1 P2)
                                (setq OS1 OS2)
;                                (setq D 2.5)
                                (setq D (GETD "CTB-1E"))
                                (setq OS2 (+ OS1 (* D FRATE)))
                                (setq P2 (GETENDPOINT P1 (* D (GRADEFACTOR P1)) OS2))
                                (setq PLIST (append PLIST (list P2)))
                                (LABELBARRIER P1 P2 "CTB-1E" (/ W 2.0))
                                (setq ENT (entlast))(RFL:PUTPREVENT ENT PREVENT)(RFL:PUTNEXTENT PREVENT ENT)(setq PREVENT ENT)
                                (setq P1 P2)
                                (setq OS1 OS2)
;                                (setq D 1.2)
                                (setq D (GETD "CBN-H"))
                                (setq OS2 (+ OS1 (* D FRATE)))
                                (setq P2 (GETENDPOINT P1 (* D (GRADEFACTOR P1)) OS2))
                                (setq PLIST (append PLIST (list P2)))
                                (LABELBARRIER P1 P2 "CBN-H" (/ W 2.0))
                                (setq ENT (entlast))(RFL:PUTPREVENT ENT PREVENT)(RFL:PUTNEXTENT PREVENT ENT)(setq PREVENT ENT)
                                (command "._PLINE")
                                (foreach P PLIST
                                 (progn
                                  (command "_NON" P)
                                 )
                                )
                                (command "")
                                (setq ENT (entlast))(RFL:PUTPREVENT ENT PREVENT)(RFL:PUTNEXTENT PREVENT ENT)(setq PREVENT ENT)
                                (setq REP "Stop")
                               )
                               (progn
                                (princ "\nCannot place nose!  Previous barrier needs to be CMB-E.")
                                (setq REP "CMB")
                               )
                              )
                             )
                             (T
                              (progn
                              )
                             )
                       )
                      )
                      ((= REP 2)
                       (if (= EH "Hook")
                        (progn
                         (setq PLIST (list P1))
;                         (setq D 1.3)
                         (setq D (GETD "CTB-2H"))
                         (setq OS2 (+ OS1 (* D FRATE)))
                         (setq P2 (GETENDPOINT P1 (* D (GRADEFACTOR P1)) OS2))
                         (setq PLIST (append PLIST (list P2)))
                         (LABELBARRIER P1 P2 "CTB-2H" (/ W 2.0))
                         (setq ENT (entlast))(RFL:PUTPREVENT ENT PREVENT)(RFL:PUTNEXTENT PREVENT ENT)(setq PREVENT ENT)
                         (setq P1 P2)
                         (setq OS1 OS2)
                         (command "._PLINE")
                         (foreach P PLIST
                          (progn
                           (command "_NON" P)
                          )
                         )
                         (command "")
                         (setq ENT (entlast))(RFL:PUTPREVENT ENT PREVENT)(RFL:PUTNEXTENT PREVENT ENT)(setq PREVENT ENT)
                         (if (= LASTPIECE "CRB") (setq REP "CMB") (setq REP "CRB"))
                         (setq EH "Eye")
                        )
                        (progn
                         (princ "\nCannot place nose!  Previous barrier needs to be EYE.")
                         (setq REP LASTPIECE)
                        )
                       )
                      )
                      ((= REP 3)
                       (if (= LASTPIECE nil)
                        (progn
                         (setq PLIST (list P1))
;                         (setq D 2.0)
                         (setq D (GETD "SP941-03.04.01"))
                         (setq OS2 (+ OS1 (* D FRATE)))
                         (setq P2 (GETENDPOINT P1 (* D (GRADEFACTOR P1)) OS2))
                         (setq PLIST (append PLIST (list P2)))
                         (LABELBARRIER P1 P2 "SP941-03.04.01" (/ W 2.0))
                         (setq ENT (entlast))(RFL:PUTPREVENT ENT PREVENT)(RFL:PUTNEXTENT PREVENT ENT)(setq PREVENT ENT)
                         (setq P1 P2)
                         (setq OS1 OS2)
                         (command "._PLINE")
                         (foreach P PLIST
                          (progn
                           (command "_NON" P)
                          )
                         )
                         (command "")
                         (setq ENT (entlast))(RFL:PUTPREVENT ENT PREVENT)(RFL:PUTNEXTENT PREVENT ENT)(setq PREVENT ENT)
                         (setq LASTPIECE "SP941-03.04.01")
                         (setq EH "Eye")
                         (setq REP "CMB")
                        )
                        (if (= EH "Hook")
                         (if (/= LASTPIECE "CRB")
                          (progn
                           (setq PLIST (list P1))
;                           (setq D 2.0)
                           (setq D (GETD "SP941-03.04.01"))
                           (setq OS2 (+ OS1 (* D FRATE)))
                           (setq P2 (GETENDPOINT P1 (* D (GRADEFACTOR P1)) OS2))
                           (setq PLIST (append PLIST (list P2)))
                           (LABELBARRIER P1 P2 "SP941-03.04.01" (/ W 2.0))
                           (setq P1 P2)
                           (setq OS1 OS2)
                           (command "._PLINE")
                           (foreach P PLIST
                            (progn
                             (command "_NON" P)
                            )
                           )
                           (command "")
                           (setq LASTPIECE "SP941-03.04.01")
                           (setq EH "Hook")
                           (setq REP "Stop")
                          )
                          (princ "\nCannot place Parapet Transition!  Previous barrier needs to be 810 mm.")
                         )
                         (princ "\nCannot place Parapet Transition!  Previous barrier needs to be EYE.")
                        )
                       )
                      )
                )
               )
              )
        )
       )
      )
      (princ "\n!!! PROBLEM CALCULATING DIRECTION !!! (WAS THE POINT ADJACENT TO THE PAINTLINE?)")
     )
    )
    (princ "\n!!! PROBLEM CALCULATING OFFSET TO POINT !!!  (IS IT ADJACENT TO PAINTLINE?)")
   )
  )
  (princ "\n!!! NOT A POLYLINE !!!")
 )

 (setvar "CMDECHO" CMDECHO)
 (setvar "ANGBASE" ANGBASE)
 (setvar "ANGDIR" ANGDIR)
 (setvar "OSMODE" OSMODE)
 (setvar "ORTHOMODE" ORTHOMODE)
 (setvar "SNAPANG" SNAPANG)
 nil
)
(defun C:COUNTBARRIER (/ BARRIERLIST C ENT ENTLIST ENTSET N1 N2 STR STRTOTAL)
 (princ "\nSelect barrier piece text entities : ")
 (setq ENTSET (ssget))
 (setq C 0)
 (setq BARRIERLIST nil)
 (setq STRTOTAL nil)
 (while (< C (sslength ENTSET))
  (setq ENT (ssname ENTSET C))
  (setq ENTLIST (entget ENT))
  (if (= (cdr (assoc 0 ENTLIST)) "TEXT")
   (if (assoc (setq STR (cdr (assoc 1 ENTLIST))) BARRIERLIST)
    (setq BARRIERLIST (subst (cons STR (1+ (cdr (assoc STR BARRIERLIST)))) (assoc STR BARRIERLIST) BARRIERLIST))
    (setq BARRIERLIST (append BARRIERLIST (list (cons STR 1))))
   )
  )
  (setq C (1+ C))
 )
 (if BARRIERLIST
  (progn
   (setq BARRIERLIST (vl-sort BARRIERLIST (function (lambda (N1 N2) (< (car N1) (car N2))))))
   (setq STRTOTAL "")
   (foreach STR BARRIERLIST
    (setq STRTOTAL (strcat STRTOTAL (car STR) " : " (itoa (cdr STR)) "\n"))
   )
   (alert STRTOTAL)
  )
 )
 (princ STRTOTAL)
 nil
)
