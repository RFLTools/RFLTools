;
;
;    Program Written by Robert Livingston 00/03/07
;
;    ALINE is a utility for attaching a line to the end of a line or arc
;
;
(defun C:ALINE (/ *error* ANG ANG1 ANG2 ANGBASE ANGDIR CMDECHO DELTA DRAWLINE
                  DX DY ENT ENTLIST L OSMODE P P1 P2 PC R R2 TMP)
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq OSMODE (getvar "OSMODE"))
 (setvar "OSMODE" 0)

 (defun *error* (msg)
  (if (>= (atof (getvar "ACADVER")) 18.2)
   (command-s "._UCS" "P")
   (command "._UCS" "P")
  )
  (setvar "CMDECHO" CMDECHO)
  (setvar "OSMODE" OSMODE)
  (setvar "ANGBASE" ANGBASE)
  (setvar "ANGDIR" ANGDIR)
  (princ msg)
  ;(setq *error* nil)
 )

 (defun DRAWLINE (P1 P2)
  (entmake (list (cons 0 "LINE")
                 (cons 10 P1)
                 (cons 11 P2)
           )
  )
 )
 
 (command "._UCS" "W")

 (setq ENT (entsel))
 (if (/= ENT nil)
  (progn
   (setq P (nth 1 ENT))
   (setq P (list (nth 0 P) (nth 1 P)))
   (setq ENT (car ENT))
   (setq ENTLIST (entget ENT))
   (if (/= (setq L (getdist "\nEnter length :")) nil)
    (progn
     (if (= (cdr (assoc 0 ENTLIST)) "LINE")
      (progn
       (setq P1 (cdr (assoc 10 ENTLIST)))
       (setq P1 (list (nth 0 P1) (nth 1 P1)))
       (setq P2 (cdr (assoc 11 ENTLIST)))
       (setq P2 (list (nth 0 P2) (nth 1 P2)))
       (if (< (distance P P2) (distance P P1))
        (progn
         (setq TMP P1)
         (setq P1 P2)
         (setq P2 TMP)
        )
       )
       (setq ANG (angle P2 P1))
       (setq P (list (+ (nth 0 P1) (+ (* L (cos ANG))))
                     (+ (nth 1 P1) (+ (* L (sin ANG))))
               )
       )
       (DRAWLINE P1 P)
      )
      (progn
       (if (= (cdr (assoc 0 ENTLIST)) "ARC")
        (progn
         (setq PC (cdr (assoc 10 ENTLIST)))
         (setq PC (list (nth 0 PC) (nth 1 PC)))
         (setq R2 (cdr (assoc 40 ENTLIST)))
         (setq ANG1 (cdr (assoc 50 ENTLIST)))
         (setq ANG2 (cdr (assoc 51 ENTLIST)))
         (setq P1 (list (+ (nth 0 PC) (* R2 (cos ANG1)))
                        (+ (nth 1 PC) (* R2 (sin ANG1)))))
         (setq ANG1 (- ANG1 (/ pi 2.0)))
         (setq P2 (list (+ (nth 0 PC) (* R2 (cos ANG2)))
                        (+ (nth 1 PC) (* R2 (sin ANG2)))))
         (setq ANG2 (+ ANG2 (/ pi 2.0)))
         (setq ANG ANG1)
         (if (< (distance P P2) (distance P P1))
          (progn
           (setq TMP P1)
           (setq P1 P2)
           (setq P2 TMP)
           (setq ANG ANG2)
          )
         )
         (setq P (list (+ (nth 0 P1) (+ (* L (cos ANG))))
                       (+ (nth 1 P1) (+ (* L (sin ANG))))
                 )
         )
         (DRAWLINE P1 P)
        )
        (progn
         (if (/= (setq ENTLIST (RFL:GETSPIRALDATA ENT)) nil)
          (progn
           (setq TMP (nth 0 (RFL:SPIRALSTAOFF P ENT)))
           (if (< (- TMP (nth 3 ENTLIST)) (- (RFL:GETSPIRALLS ENT) TMP))
            (progn
             (setq P1 (RFL:SPIRALXY (list (nth 3 ENTLIST) 0.0) ENT))
             (setq ANG (angle (nth 1 ENTLIST) (nth 0 ENTLIST)))
             (if (> (nth 3 ENTLIST) 0.0)
              (progn
               (if (> (sin (- (angle (nth 1 ENTLIST) (nth 0 ENTLIST)) (angle (nth 2 ENTLIST) (nth 1 ENTLIST)))) 0.0)
                (setq TMP -1.0)
                (setq TMP 1.0)
               )
               (setq ANG (+ ANG
                            (* TMP
                               (expt (nth 3 ENTLIST) 2)
                               (RFL:GETSPIRALTHETA ENT)
                               (/ 1.0 (expt (RFL:GETSPIRALLS ENT) 2))
                            )
                         )
               )
              )
             )
            )
            (progn
             (setq P1 (nth 2 ENTLIST))
             (setq ANG (angle (nth 1 ENTLIST) (nth 2 ENTLIST)))
            )
           )
           (setq P (list (+ (nth 0 P1) (* L (cos ANG)))
                         (+ (nth 1 P1) (* L (sin ANG)))))
           (DRAWLINE P1 P)
          )
          (progn
           (princ "\n*** ENTITY NOT SPIRAL/ARC/LINE ***")
          )
         )
        )
       )
      )
     )
    )
   )
  )
 )

 (command "._UCS" "P")
 (setvar "CMDECHO" CMDECHO)
 (setvar "ANGBASE" ANGBASE)
 (setvar "ANGDIR" ANGDIR)
 (setvar "OSMODE" OSMODE)
 (setq P2 P2)
)
