;
;
;     Program written by Robert Livingston, 2011/11/22
;
;     RAB2C3D writes the current RFL alignment to a C3D Drawing.
;
;
(defun C:RAB2C3D (/ *error* ALIGNLISTSAVE ALIGNMENTNAME ALIGNMENTSTYLENAME ALIGNMENTLABELSTYLESETNAME BLKENT BLKENTLIST BULGE
                    C CCW CMAX GETOBAECC ID LANDPROFILESTYLENAME LO LS NAME NODE
                    OALIGNMENT OALIGNMENTENTITIES OALIGNMENTSTYLES OALIGNMENTLABELSTYLESETS OALIGNMENTSSITELESS OCIVILAPP ODOCUMENT OLANDPROFILESTYLES OPVIS
                    P1 P2 PLT PLTST PST PREVENT PVILISTSAVE RADIUS SUPERLISTSAVE)
 (setq CMDECHO (getvar "CMDECHO"))
 (setvar "CMDECHO" 0)

 (defun *error* (msg)
  (setvar "CMDECHO" CMDECHO)
  (setq *error* nil)
  (setq RFL:ALIGNLIST ALIGNLISTSAVE)
  (setq RFL:PVILIST PVILISTSAVE)
  (setq RFL:SUPERLIST SUPERLISTSAVE)
  (princ msg)
 )

 (defun GETOBAECC (/ *acad* ACADACTIVEDOCUMENT ACADPROD ACADVER C3DOBJECT C3DDOC C3DSURFS C CMAX c3DSURF)
  (princ "\n")
  (setq ACADPROD (vlax-product-key))
  (setq ACADVER (RFL:ACADVER))
  (setq ACADPROD (strcat "AeccXUiLand.AeccApplication." ACADVER))
  (setq *acad* (vlax-get-acad-object))
  (vla-getinterfaceobject *acad* ACADPROD)
 )

 (defun RADIUS (P1 P2 BULGE / ATOTAL CHORD R)
  (if (listp BULGE)
   (setq R (RFL:GETSPIRALR2 (nth 0 BULGE) (nth 1 BULGE) (nth 2 BULGE)))
   (progn
    (setq ATOTAL (* 4.0 (atan (abs BULGE))))
    (setq CHORD (distance P1 P2))
    (if (< (abs BULGE) TOL)
     (setq R nil)
     (setq R (/ CHORD (* 2 (sin (/ ATOTAL 2)))))
    )
   )
  )
  R
 )

 (command "._UNDO" "M")
 (setq ALIGNLISTSAVE RFL:ALIGNLIST)
 (setq PVILISTSAVE RFL:PVILIST)
 (setq SUPERLISTSAVE RFL:SUPERLIST)

 (setq BLKENT (car (entsel "\nSelect RFL Alignment Block <return to use current alignment> : ")))
 (if (= nil BLKENT)
  (progn
   (setq ALIGNMENTNAME "RFL Alignment")
  )
  (progn
   (setq BLKENTLIST (entget BLKENT))
   (if (and (= "INSERT" (cdr (assoc 0 BLKENTLIST))) (= "RFLALIGN" (strcase (cdr (assoc 2 BLKENTLIST)))))
    (progn
     (RFL:RALIGNB BLKENT)
     (RFL:RPROFB BLKENT)
     (RFL:RSUPERB BLKENT)
     (setq BLKENT (entnext BLKENT))
     (setq BLKENTLIST (entget BLKENT))
     (setq ALIGNMENTNAME "")
     (while (and (= "ATTRIB" (cdr (assoc 0 BLKENTLIST))) (/= "TITLE" (cdr (assoc 2 BLKENTLIST))))
      (setq BLKENT (entnext BLKENT))
      (setq BLKENTLIST (entget BLKENT))
     )
     (if (= "TITLE" (cdr (assoc 2 BLKENTLIST)))
      (setq ALIGNMENTNAME (cdr (assoc 1 BLKENTLIST)))
     )
    )
    (princ "\n*** NOT AN RFL ALIGNMENT BLOCK ***")
   )
  )
 )

 (if (= nil RFL:ALIGNLIST)
  (princ "\n*****  NO RFL ALIGNMENT DEFINED  *****")
  (progn
   (textscr)
   (setq NAME (getstring T (strcat "\nEnter new alignment name <" ALIGNMENTNAME "> : ")))
   (if (= NAME "") (setq NAME ALIGNMENTNAME))
   (if (/= "" NAME)
    (progn
     (setq OCIVILAPP (GETOBAECC))
     (if (= nil OCIVILAPP)
      (alert "C3D not loaded!")
      (progn
       (setq ODOCUMENT (vlax-get-property OCIVILAPP "ActiveDocument"))
       (if (= nil ODOCUMENT)
        (alert "Error getting Document!")
        (progn
         (setq OALIGNMENTSTYLES (vlax-get-property ODOCUMENT "AlignmentStyles"))
         (if (= nil OALIGNMENTSTYLES)
          (alert "Error getting Alignment Styles!")
          (progn
           (setq CMAX (vlax-get-property OALIGNMENTSTYLES "Count"))
           (setq C 0)
           (while (< C CMAX)
            (princ (strcat (itoa (+ C 1)) " : " (vlax-get-property (vlax-get-property OALIGNMENTSTYLES "Item" C) "Name") "\n"))
            (setq C (+ C 1))
           )
           (setq C 0)
           (while (or (< C 1) (> C CMAX))
            (setq C (getint (strcat "Select Alignment Style < 1 to " (itoa CMAX) " > : ")))
           )
           (setq C (- C 1))
           (setq ALIGNMENTSTYLENAME (vlax-get-property (vlax-get-property OALIGNMENTSTYLES "Item" C) "Name"))
           (princ "\n")
           (setq OALIGNMENTLABELSTYLESETS (vlax-get-property ODOCUMENT "AlignmentLabelStyleSets"))
           (if (= nil OALIGNMENTLABELSTYLESETS)
            (alert "Error getting Alignment Label Style Sets!")
            (progn
             (setq CMAX (vlax-get-property OALIGNMENTLABELSTYLESETS "Count"))
             (setq C 0)
             (while (< C CMAX)
              (princ (strcat (itoa (+ C 1)) " : " (vlax-get-property (vlax-get-property OALIGNMENTLABELSTYLESETS "Item" C) "Name") "\n"))
              (setq C (+ C 1))
             )
             (setq C 0)
             (while (or (< C 1) (> C CMAX))
              (setq C (getint (strcat "Select Alignment Label Style Set < 1 to " (itoa CMAX) " > : ")))
             )
             (setq C (- C 1))
             (setq ALIGNMENTLABELSTYLESETNAME (vlax-get-property (vlax-get-property OALIGNMENTLABELSTYLESETS "Item" C) "Name"))
             (setq OALIGNMENTSSITELESS (vlax-get-property ODOCUMENT "AlignmentsSiteless"))
             (if (= nil OALIGNMENTSSITELESS)
              (alert "Error getting Alignments!")
              (progn
               (setq OALIGNMENT (vlax-invoke-method OALIGNMENTSSITELESS "Add" NAME (getvar "CLAYER") ALIGNMENTSTYLENAME ALIGNMENTLABELSTYLESETNAME))
               (if (= nil OALIGNMENT)
                (alert "Error creating new alignment!")
                (progn
                 (vlax-put-property OALIGNMENT "ReferencePointStation" (caar RFL:ALIGNLIST))
                 (setq OALIGNMENTENTITIES (vlax-get-property OALIGNMENT "Entities"))
                 (if (= nil OALIGNMENTENTITIES)
                  (alert "Error accessing entities!")
                  (progn
                   (setq PREVENT nil)
                   (setq C 0)
                   (while (< C (length RFL:ALIGNLIST))
                    (setq NODE (nth C RFL:ALIGNLIST))
                    (setq BULGE (nth 3 NODE))
                    (if (listp BULGE)
                     (progn  ;  Spiral
                      (setq P1 (nth 1 NODE))
                      (setq P2 (nth 2 NODE))
                      (setq PLT (nth 0 BULGE))
                      (setq PLTST (nth 1 BULGE))
                      (setq PST (nth 2 BULGE))
                      (setq LO (nth 3 BULGE))
                      (setq LS (- (RFL:GETSPIRALLS2 PLT PLTST PST) LO))
                      (if (> (distance P2 PLT) (distance P1 PLT))
                       (progn
                        (setq R2 (RADIUS P1 P2 BULGE))
                        (if (< LO RFL:TOLFINE)
                         (setq R1 0.0)
                         (setq R1 (/ (* R2 (RFL:GETSPIRALLS2 PLT PLTST PST)) LO))
                        )
                       )
                       (progn
                        (setq R1 (RADIUS P1 P2 BULGE))
                        (if (< LO RFL:TOLFINE)
                         (setq R2 0.0)
                         (setq R2 (/ (* R1 (RFL:GETSPIRALLS2 PLT PLTST PST)) LO))
                        )
                       )
                      )
                      (if (< (abs LO) RFL:TOLFINE) (setq LO 0.0))
                      (setq PLTST (RFL:GETSPIRALPI2 LO PLT PLTST PST))
                      (setq PT1 (vlax-make-safearray vlax-vbDouble '(0 . 2)))
                      (vlax-safearray-put-element PT1 0 (car P1))
                      (vlax-safearray-put-element PT1 1 (cadr P1))
                      (vlax-safearray-put-element PT1 2 0.0)
                      (setq PT2 (vlax-make-safearray vlax-vbDouble '(0 . 2)))
                      (vlax-safearray-put-element PT2 0 (car PLTST))
                      (vlax-safearray-put-element PT2 1 (cadr PLTST))
                      (vlax-safearray-put-element PT2 2 0.0)
                      (if (> (sin (- (angle PLTST P2) (angle P1 PLTST))) 0.0)
                       (setq CCW 0)
                       (setq CCW T)
                      )
                      (if (= nil PREVENT)
                       (setq ID 0)
                       (setq ID (vlax-get-property PREVENT "Id"))
                      )
                      (if (= 0.0 R1)
                       (setq PREVENT (vlax-invoke-method OALIGNMENTENTITIES "AddFixedSpiral1" ID PT1 PT2 R2 LS 1 CCW 1))
                       (if (= 0.0 R2)
                        (setq PREVENT (vlax-invoke-method OALIGNMENTENTITIES "AddFixedSpiral1" ID PT1 PT2 R1 LS 2 CCW 1))
                        (setq PREVENT (vlax-invoke-method OALIGNMENTENTITIES "AddFixedSpiral2" ID PT1 PT2 R1 R2 LS CCW 1))
                       )
                      )
                     )
                     (if (< (abs BULGE) RFL:TOLFINE)
                      (progn  ;  Tangent
                       (setq PT1 (vlax-make-safearray vlax-vbDouble '(0 . 2)))
                       (vlax-safearray-put-element PT1 0 (car (nth 1 NODE)))
                       (vlax-safearray-put-element PT1 1 (cadr (nth 1 NODE)))
                       (vlax-safearray-put-element PT1 2 0.0)
                       (setq PT2 (vlax-make-safearray vlax-vbDouble '(0 . 2)))
                       (vlax-safearray-put-element PT2 0 (car (nth 2 NODE)))
                       (vlax-safearray-put-element PT2 1 (cadr (nth 2 NODE)))
                       (vlax-safearray-put-element PT2 2 0.0)
                       (setq PREVENT (vlax-invoke-method OALIGNMENTENTITIES "AddFixedLine1" PT1 PT2))
                      )
                      (progn  ;  Arc
                       (setq PT1 (vlax-make-safearray vlax-vbDouble '(0 . 2)))
                       (vlax-safearray-put-element PT1 0 (car (nth 1 NODE)))
                       (vlax-safearray-put-element PT1 1 (cadr (nth 1 NODE)))
                       (vlax-safearray-put-element PT1 2 0.0)
                       (setq PT2 (vlax-make-safearray vlax-vbDouble '(0 . 2)))
                       (vlax-safearray-put-element PT2 0 (car (nth 2 NODE)))
                       (vlax-safearray-put-element PT2 1 (cadr (nth 2 NODE)))
                       (vlax-safearray-put-element PT2 2 0.0)
                       (setq PC (RFL:CENTER (nth 1 NODE) (nth 2 NODE) BULGE))
                       (setq PT3  (vlax-make-safearray vlax-vbDouble '(0 . 2)))
                       (vlax-safearray-put-element PT3 0 (car PC))
                       (vlax-safearray-put-element PT3 1 (cadr PC))
                       (vlax-safearray-put-element PT3 2 0.0)
                       (if (> BULGE 0.0) (setq CCW 0) (setq CCW T))
                       (setq PREVENT (vlax-invoke-method OALIGNMENTENTITIES "AddFixedCurve6" PT1 PT2 (RADIUS (nth 1 NODE) (nth 2 NODE) BULGE) CCW))
                      )
                     )
                    )
                    (setq C (+ C 1))
                   )
                   (if (/= nil RFL:PVILIST)
                    (progn
                     (setq OPROFILES (vlax-get-property OALIGNMENT "Profiles"))
                     (setq OLANDPROFILESTYLES (vlax-get-property ODOCUMENT "LandProfileStyles"))
                     (if (= nil OLANDPROFILESTYLES)
                      (alert "Error getting Profile Styles!")
                      (progn
                       (setq CMAX (vlax-get-property OLANDPROFILESTYLES "Count"))
                       (setq C 0)
                       (while (< C CMAX)
                        (princ (strcat (itoa (+ C 1)) " : " (vlax-get-property (vlax-get-property OLANDPROFILESTYLES "Item" C) "Name") "\n"))
                        (setq C (+ C 1))
                       )
                       (setq C 0)
                       (while (or (< C 1) (> C CMAX))
                        (setq C (getint (strcat "Select Profile Style < 1 to " (itoa CMAX) " > : ")))
                       )
                       (setq C (- C 1))
                       (setq LANDPROFILESTYLENAME (vlax-get-property (vlax-get-property OLANDPROFILESTYLES "Item" C) "Name"))
                       (princ "\n")
                       (setq OPROFILE (vlax-invoke-method OPROFILES "Add" NAME 2 LANDPROFILESTYLENAME))
                       (setq OPVIS (vlax-get-property OPROFILE "PVIs"))
                       (setq NODE (car RFL:PVILIST))
                       (vlax-invoke-method OPVIS "Add" (nth 0 NODE) (nth 1 NODE) 1)
                       (setq NODE (last RFL:PVILIST))
                       (vlax-invoke-method OPVIS "Add" (nth 0 NODE) (nth 1 NODE) 1)
                       (setq C 1)
                       (while (< C (- (length RFL:PVILIST) 1))
                        (setq NODE (nth C RFL:PVILIST))
                        (if (< (nth 3 NODE) RFL:TOLFINE)
                         (vlax-invoke-method OPVIS "Add" (nth 0 NODE) (nth 1 NODE) 1)
                         (vlax-invoke-method OPVIS "Add" (nth 0 NODE) (nth 1 NODE) 3 (nth 3 NODE))
                        )
                        (setq C (+ C 1))
                       )
                      )
                     )
                    )
                   )
;                   (if (/= nil RFL:SUPERLIST)
;                    (progn
;                     (setq OSUPERELEVATIONDATA (vlax-get-property OALIGNMENT "SuperelevationData"))
;                     (setq C 0)
;                     (while (< C (length RFL:SUPERLIST))
;                      (setq NODE (nth C RFL:SUPERLIST))
;                      (setq SUPERDATA (vlax-make-variant vlax-vbArray))
;                      (vlax-invoke-method OSUPERELEVATIONDATA "Add" (car NODE) SUPERDATA)
;                      (setq C (+ C 1))
;                     )
;                    )
;                   )
                  )
                 )
                )
               )
              )
             )
            )
           )
          )
         )
        )
       )
      )
     )
    )
   )
  )
 )

 (graphscr)
 (setq RFL:ALIGNLIST ALIGNLISTSAVE)
 (setq RFL:PVILIST PVILISTSAVE)
 (setq RFL:SUPERLIST SUPERLISTSAVE)
 (eval T)
)
