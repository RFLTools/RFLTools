;
;
;   Program written by Robert Livingston, 00/09/18
;
;   VC3P is a utility for drawing vertical curves through 3 points
;
;
(defun C:VC3P (/ A B CMDECHO ENT1 ENT2 G1 G2 L OSMODE P1 P2 P3 P1 VCURVE VEXAG X1 X2 Y1 Y2 TMP Z1 Z2 Z3)
 (setq CMDECHO (getvar "CMDECHO"))
 (setvar "CMDECHO" 0)
 (setq OSMODE (getvar "OSMODE"))

 (defun VCURVE (ENT1 ENT2 VEXAG L / ATTREQ ENT ENTLIST G1 G2 K P P1 P2 P3 P4 SPLINETYPE SPLINESEGS TMP)
  (setq ATTREQ (getvar "ATTREQ"))
  (setvar "ATTREQ" 1)
  (setq SPLINETYPE (getvar "SPLINETYPE"))
  (setvar "SPLINETYPE" 5)
  (setq SPLINESEGS (getvar "SPLINESEGS"))
  (setvar "SPLINESEGS" 65)

  (setq ENTLIST (entget ENT1))
  (setq P1 (cdr (assoc 10 ENTLIST)))
  (setq P2 (cdr (assoc 11 ENTLIST)))
  (setq ENTLIST (entget ENT2))
  (setq P3 (cdr (assoc 10 ENTLIST)))
  (setq P4 (cdr (assoc 11 ENTLIST)))
  (setq P (inters P1 P2 P3 P4 nil))
  (if (/= nil P)
   (progn
    (if (> (distance P2 P) (distance P1 P))
     (setq P1 P2)
    )
    (if (> (distance P3 P) (distance P4 P))
     (setq P4 P3)
    )
    (setq G1 (/ (- (nth 1 P) (nth 1 P1))
                (- (nth 0 P) (nth 0 P1))
                VEXAG
             )
    )
    (setq G2 (/ (- (nth 1 P4) (nth 1 P))
                (- (nth 0 P4) (nth 0 P))
                VEXAG
             )
    )
    (setq K (abs (/ L (- G2 G1) 100.0)))
    (setvar "ATTREQ" 0)
    (if (= nil (tblsearch "BLOCK" "PVI2")) (RFL:MAKEENT "PVI2"))
    (command "._INSERT"
             "PVI2"
             P
             25.4
             25.4
             0.0
    )
    (setq ENT (entlast))
    (setq ENTLIST (entget ENT))
    (if (= (cdr (assoc 66 ENTLIST)) 1)
     (progn
      (setq ENT (entnext ENT))
      (setq ENTLIST (entget ENT))
      (while (/= (cdr (assoc 0 ENTLIST)) "SEQEND")
       (if (= (cdr (assoc 2 ENTLIST)) "LENGTH")
        (progn
         (setq ENTLIST (subst (cons 1 (rtos L 2 8)) (assoc 1 ENTLIST) ENTLIST))
         (entmod ENTLIST)
         (entupd ENT)
        )
       )
       (if (= (cdr (assoc 2 ENTLIST)) "K")
        (progn
         (setq ENTLIST (subst (cons 1 (rtos K 2 8)) (assoc 1 ENTLIST) ENTLIST))
         (entmod ENTLIST)
         (entupd ENT)
        )
       )
       (setq ENT (entnext ENT))
       (setq ENTLIST (entget ENT))
      )
     )
    )
    (setvar "ATTREQ" 1)
    (setq P2 (list (- (nth 0 P) (/ L 2.0))
                   (- (nth 1 P) (* (/ L 2.0) G1 VEXAG))
             )
    )
    (setq P3 (list (+ (nth 0 P) (/ L 2.0))
                   (+ (nth 1 P) (* (/ L 2.0) G2 VEXAG))
             )
    )
    (command "._PLINE" P2 P P3 "")
    (setq ENT (entlast))
    (command "._PEDIT" ENT "S" "")
   )
  )
  (setvar "ATTREQ" ATTREQ)
  (setvar "SPLINETYPE" SPLINETYPE)
  (setvar "SPLINESEGS" SPLINESEGS)
 )

 (setq VEXAG (getreal "Vertical exageration <10.000> :"))
 (if (= nil VEXAG) (setq VEXAG 10.0))
 (setq P1 (getpoint "\nFirst point :"))
 (setq P2 (getpoint "\nSecond point :"))
 (setq P3 nil K nil)
 (while (or (= P3 nil) (= K nil))
  (if (= P3 nil)
   (progn
    (setq P3 (getpoint "\nThird point (<Return> to enter K) :"))
    (if (= P3 nil)
     (setq P3 1)
     (setq K 1)
    )
   )
   (progn
    (setq K (getreal "\nK (<Return> to enter third point) :"))
    (if (= K nil)
     (setq P3 nil)
     (progn
      (setq L (/ (- (nth 0 P2) (nth 0 P1)) 2.0))
      (setq Z1 (/ (nth 1 P1) VEXAG))
      (setq Z3 (/ (nth 1 P2) VEXAG))
      (setq Z2 (* (/ (+ Z1 Z3 (/ (* L L) (* 100.0 K))) 2.0) VEXAG))
      (setq P3 (list (+ (nth 0 P1) L) Z2 0.0))
     )
    )
   )
  )
 )
 (setvar "OSMODE" 0)
 (if (< (nth 0 P2) (nth 0 P1))
  (progn
   (setq TMP P1)
   (setq P1 P2)
   (setq P2 TMP)
  )
 )
 (if (< (nth 0 P3) (nth 0 P1))
  (progn
   (setq TMP P1)
   (setq P1 P3)
   (setq P3 TMP)
  )
 )
 (if (< (nth 0 P3) (nth 0 P2))
  (progn
   (setq TMP P2)
   (setq P2 P3)
   (setq P3 TMP)
  )
 )
 (setq X1 (- (nth 0 P2) (nth 0 P1)))
 (setq Y1 (/ (- (nth 1 P2) (nth 1 P1)) VEXAG))
 (setq X2 (- (nth 0 P3) (nth 0 P1)))
 (setq Y2 (/ (- (nth 1 P3) (nth 1 P1)) VEXAG))

 (setq A (/ (- (/ Y2 X2)
               (/ Y1 X1)
            )
            (- X2 X1)
         )
 )
 (setq B (/ (- (/ Y2 (* X2 X2))
               (/ Y1 (* X1 X1))
            )
            (- (/ 1.0 X2)
               (/ 1.0 X1)
            )
         )
 )

 (setq G1 (* B 100.0))
 (setq G2 (* (+ (* 2.0 A X2) B) 100.0))

 (setq TMP nil)
 (setq TMP (getreal (strcat "G1 = " (rtos G1) ", desired (<return> to accept) : ")))
 (if (/= TMP nil)
  (setq G1 TMP)
 )
 (setq TMP nil)
 (setq TMP (getreal (strcat "G2 = " (rtos G2) ", desired (<return> to accept) : ")))
 (if (/= TMP nil)
  (setq G2 TMP)
 )

 (setq X1 (/ (- (/ G1 100.0)
                B
             )
             (* 2.0 A)
          )
 )
 (setq Y1 (+ (* A X1 X1)
             (* B X1)
          )
 )
 (setq X2 (/ (- (/ G2 100.0)
                B
             )
             (* 2.0 A)
          )
 )
 (setq Y2 (+ (* A X2 X2)
             (* B X2)
          )
 )
 (setq P2 (list (+ (nth 0 P1) X2)
                (+ (nth 1 P1)
                   (* VEXAG Y2)
                )
          )
 )
 (setq P1 (list (+ (nth 0 P1) X1)
                (+ (nth 1 P1)
                   (* VEXAG Y1)
                )
          )
 )
 (setq P3 (list (+ (nth 0 P1)
                   (/ (- (nth 0 P2) (nth 0 P1))
                      2.0
                   )
                )
                (+ (nth 1 P1)
                   (* (/ (- (nth 0 P2) (nth 0 P1))
                         2.0
                      )
                      (/ G1 100.0)
                      VEXAG
                   )
                )
          )
 )
 (command "._LINE" P1 P3 "")
 (setq ENT1 (entlast))
 (command "._LINE" P3 P2 "")
 (setq ENT2 (entlast))
 (VCURVE ENT1 ENT2 VEXAG (- X2 X1))

 (setvar "CMDECHO" CMDECHO)
 (setvar "OSMODE" OSMODE)
)
