;
;
;     Program written by Robert Livingston, 03/05/12
;
;     DAYLIGHT is a utility for 'Daylighting' 3D Polylines
;
;
(setq RFL:DAYLIGHTLIST (list (cons "DITCHBACK" 6.0)
                             (cons "DITCHWIDTH" 4.0)
                             (cons "DITCHDEPTH" 1.0)
                             (cons "USEDITCH" "1")
                             (cons "FS7" 3.0)
                             (cons "FD6" 6.5)
                             (cons "FS5" 4.0)
                             (cons "FD4" 4.0)
                             (cons "FS3" 5.0)
                             (cons "FD2" 2.5)
                             (cons "FS1" 6.0)
                             (cons "CS1" 5.0)
                             (cons "CD2" 2.0)
                             (cons "CS3" 3.0)
                             (cons "SWATH" 100.0)))
(defun C:DAYLIGHT (/ AECCOBJ ACCEPTDAYLIGHT ANGBASE ANGDIR *error* C CANCEL CANCELDAYLIGHT CATCHLINE
                     CHECKENABLE CHECKNUMBER CMDECHO CURRENTSURFACE
                     DCL_ID ENT ENTLIST GETFROMLIST NODE OBSURFACE OGLINE OGLINELIST OGOFFSETLIST OS OS1 OS2 OSMODE
                     P P1 P2 PD1 PD2 SA1 SA2 STA V1 V2 Z Z1 Z2)
 (setq CMDECHO (getvar "CMDECHO"))
 (setvar "CMDECHO" 0)
 (setq ANGBASE (getvar "ANGBASE"))
 (setvar "ANGBASE" 0.0)
 (setq ANGDIR (getvar "ANGDIR"))
 (setvar "ANGDIR" 0)
 (setq DIMZIN (getvar "DIMZIN"))
 (setvar "DIMZIN" 0)
 (setq OSMODE (getvar "OSMODE"))
 (setvar "OSMODE" 0)

 (command "._UNDO" "M")

 (defun *error* (msg)
  (setvar "CMDECHO" CMDECHO)
  (setvar "OSMODE" OSMODE)
  (setvar "ANGBASE" ANGBASE)
  (setvar "ANGDIR" ANGDIR)
  (setvar "DIMZIN" DIMZIN)
  (princ msg)
  ;(setq *error* nil)
 )

 (defun GETSLOPEINT (OFFSET ELEV SLOPE OGLIST / C ELEV1 ELEV2 ELEV3 OFFSET1 OFFSET2 OFFSET3 TOL)
  (setq TOL 0.000001)
  (setq C 0)
  (setq OFFSET3 nil)
  (setq ELEV3 nil)
  (while (< C (- (length OGLIST) 1))
   (setq OFFSET1 (car (nth C OGLIST)))
   (setq ELEV1 (cadr (nth C OGLIST)))
   (setq OFFSET2 (car (nth (+ C 1) OGLIST)))
   (setq ELEV2 (cadr (nth (+ C 1) OGLIST)))
   (if (< (abs (- OFFSET2 OFFSET1)) TOL)
    (setq C (+ C 1))
    (progn
     (setq OFFSET3 (/ (- (+ (* OFFSET1
                               (/ (- ELEV2 ELEV1)
                                  (- OFFSET2 OFFSET1)
                               )
                            )
                            ELEV
                         )
                         (+ (/ OFFSET SLOPE) ELEV1)
                      )
                      (- (/ (- ELEV2 ELEV1)
                            (- OFFSET2 OFFSET1)
                         )
                         (/ 1.0 SLOPE)
                      )
                   )
     )
     (setq ELEV3 (+ ELEV
                    (/ (- OFFSET3 OFFSET)
                       SLOPE
                    )
                 )
     )
     (if (>= (* (- OFFSET3 OFFSET1) (- OFFSET2 OFFSET3)) 0.0)
      (setq C (length OGLIST))
      (setq C (+ C 1))
     )
    )
   )
  )
  (list OFFSET3 ELEV3)
 )

 (defun GETFILLPOINT ()
  (setq P2 (GETSLOPEINT OS1 Z1 (* -1.0 (RFL:SIGN OS1) (cdr (assoc "FS1" RFL:DAYLIGHTLIST))) OGOFFSETLIST))
  (if (/= nil P2)
   (if (>= (- Z1 (cadr P2)) (cdr (assoc "FD2" RFL:DAYLIGHTLIST)))
    (progn
     (setq P2 (GETSLOPEINT OS1 Z1 (* -1.0 (RFL:SIGN OS1) (cdr (assoc "FS3" RFL:DAYLIGHTLIST))) OGOFFSETLIST))
     (if (>= (- Z1 (cadr P2)) (cdr (assoc "FD4" RFL:DAYLIGHTLIST)))
      (progn
       (setq P2 (GETSLOPEINT OS1 Z1 (* -1.0 (RFL:SIGN OS1) (cdr (assoc "FS5" RFL:DAYLIGHTLIST))) OGOFFSETLIST))
       (if (>= (- Z1 (cadr P2)) (cdr (assoc "FD6" RFL:DAYLIGHTLIST)))
        (setq P2 (GETSLOPEINT OS1 Z1 (* -1.0 (RFL:SIGN OS1) (cdr (assoc "FS7" RFL:DAYLIGHTLIST))) OGOFFSETLIST))
       )
      )
     )
    )
   )
  )
 )

 (defun GETCUTPOINT ()
  (setq P2 (GETSLOPEINT OS1 Z1 (* (RFL:SIGN OS1) (cdr (assoc "CS1" RFL:DAYLIGHTLIST))) OGOFFSETLIST))
  (if (/= nil P2)
   (if (>= (- (cadr P2) Z1) (cdr (assoc "CD2" RFL:DAYLIGHTLIST)))
    (setq P2 (GETSLOPEINT OS1 Z1 (* (RFL:SIGN OS1) (cdr (assoc "CS3" RFL:DAYLIGHTLIST))) OGOFFSETLIST))
   )
  )
 )

 (defun CHECKENABLE ()
  (if (= "1" (get_tile "USEDITCH"))
   (progn
    (mode_tile "DITCHBACK" 0)
    (mode_tile "DITCHWIDTH" 0)
    (mode_tile "DITCHDEPTH" 0)
   )
   (progn
    (mode_tile "DITCHBACK" 1)
    (mode_tile "DITCHWIDTH" 1)
    (mode_tile "DITCHDEPTH" 1)
   )
  )
 )

 (defun CHECKNUMBER (TILE)
  (set_tile TILE (rtos (atof (get_tile TILE))))
 )

 (defun ACCEPTDAYLIGHT ()
  (setq RFL:DAYLIGHTLIST (list (cons "DITCHBACK" (atof (get_tile "DITCHBACK")))
                               (cons "DITCHWIDTH" (atof (get_tile "DITCHWIDTH")))
                               (cons "DITCHDEPTH" (atof (get_tile "DITCHDEPTH")))
                               (cons "USEDITCH" (get_tile "USEDITCH"))
                               (cons "FS7" (atof (get_tile "FS7")))
                               (cons "FD6" (atof (get_tile "FD6")))
                               (cons "FS5" (atof (get_tile "FS5")))
                               (cons "FD4" (atof (get_tile "FD4")))
                               (cons "FS3" (atof (get_tile "FS3")))
                               (cons "FD2" (atof (get_tile "FD2")))
                               (cons "FS1" (atof (get_tile "FS1")))
                               (cons "CS1" (atof (get_tile "CS1")))
                               (cons "CD2" (atof (get_tile "CD2")))
                               (cons "CS3" (atof (get_tile "CS3")))
                               (cons "SWATH" (atof (get_tile "SWATH")))))

  (done_dialog)
  (unload_dialog DCL_ID)
  (setq CANCEL nil)
 )

 (defun CANCELDAYLIGHT ()
  (done_dialog)
  (unload_dialog DCL_ID)
  (setq CANCEL 1)
 )

 (setq OBSURFACE (RFL:GETC3DSURFACE))
 
 (if (or (= nil OBSURFACE) (= nil RFL:ALIGNLIST))
  (princ "\n***** ERROR WITH SURFACE OR ALIGNMENT *****")
  (progn
   (setq ENT (car (entsel "\nSelect 3D polyline :")))
   (if (/= ENT nil)
    (progn
     (setq ENTLIST (entget ENT))
     (if (= (cdr (assoc 0 ENTLIST)) "POLYLINE")
      (progn
       (if (= 0 (logand (cdr (assoc 70 ENTLIST)) 8))
        (princ "\n***** NOT A 3D POLYLINE *****")
        (progn

         (if (= DAYLIGHTDCLNAME nil)
          (progn
           (setq DAYLIGHTDCLNAME (vl-filename-mktemp "rfl.dcl"))
           (RFL:MAKEDCL DAYLIGHTDCLNAME "DAYLIGHT")
          )
          (if (= nil (findfile DAYLIGHTDCLNAME))
           (progn
            (setq DAYLIGHTDCLNAME (vl-filename-mktemp "rfl.dcl"))
            (RFL:MAKEDCL DAYLIGHTDCLNAME "DAYLIGHT")
           )
          )
         )

         (setq DCL_ID (load_dialog DAYLIGHTDCLNAME))
         (if (not (new_dialog "DAYLIGHT" DCL_ID)) (exit))

         (set_tile "DITCHBACK" (rtos (cdr (assoc "DITCHBACK" RFL:DAYLIGHTLIST))))
         (set_tile "DITCHWIDTH" (rtos (cdr (assoc "DITCHWIDTH" RFL:DAYLIGHTLIST))))
         (set_tile "DITCHDEPTH" (rtos (cdr (assoc "DITCHDEPTH" RFL:DAYLIGHTLIST))))
         (set_tile "USEDITCH" (cdr (assoc "USEDITCH" RFL:DAYLIGHTLIST)))
         (set_tile "FS7" (rtos (cdr (assoc "FS7" RFL:DAYLIGHTLIST))))
         (set_tile "FD6" (rtos (cdr (assoc "FD6" RFL:DAYLIGHTLIST))))
         (set_tile "FS5" (rtos (cdr (assoc "FS5" RFL:DAYLIGHTLIST))))
         (set_tile "FD4" (rtos (cdr (assoc "FD4" RFL:DAYLIGHTLIST))))
         (set_tile "FS3" (rtos (cdr (assoc "FS3" RFL:DAYLIGHTLIST))))
         (set_tile "FD2" (rtos (cdr (assoc "FD2" RFL:DAYLIGHTLIST))))
         (set_tile "FS1" (rtos (cdr (assoc "FS1" RFL:DAYLIGHTLIST))))
         (set_tile "CS1" (rtos (cdr (assoc "CS1" RFL:DAYLIGHTLIST))))
         (set_tile "CD2" (rtos (cdr (assoc "CD2" RFL:DAYLIGHTLIST))))
         (set_tile "CS3" (rtos (cdr (assoc "CS3" RFL:DAYLIGHTLIST))))
         (set_tile "SWATH" (rtos (cdr (assoc "SWATH" RFL:DAYLIGHTLIST))))

         (CHECKENABLE)

         (action_tile "DITCHBACK" "(CHECKNUMBER \"DITCHBACK\")")
         (action_tile "DITCHWIDTH" "(CHECKNUMBER \"DITCHWIDTH\")")
         (action_tile "DITCHDEPTH" "(CHECKNUMBER \"DITCHDEPTH\")")
         (action_tile "USEDITCH" "(CHECKENABLE)")
         (action_tile "FS7" "(CHECKNUMBER \"FS7\")")
         (action_tile "FD6" "(CHECKNUMBER \"FD6\")")
         (action_tile "FS5" "(CHECKNUMBER \"FS5\")")
         (action_tile "FD4" "(CHECKNUMBER \"FD4\")")
         (action_tile "FS3" "(CHECKNUMBER \"FS3\")")
         (action_tile "FD2" "(CHECKNUMBER \"FD2\")")
         (action_tile "FS1" "(CHECKNUMBER \"FS1\")")
         (action_tile "CS1" "(CHECKNUMBER \"CS1\")")
         (action_tile "CD2" "(CHECKNUMBER \"CD2\")")
         (action_tile "CS3" "(CHECKNUMBER \"CS3\")")
         (action_tile "SWATH" "(CHECKNUMBER \"SWATH\")")

         (action_tile "OK" "(ACCEPTDAYLIGHT)")
         (action_tile "CANCEL" "(CANCELDAYLIGHT)")

         (start_dialog)

         (if (= nil CANCEL)
          (progn
           (setq CATCHLINE nil)
           (setq ENT (entnext ENT))
           (setq ENTLIST (entget ENT))
           (setq SA1 (vlax-make-safearray vlax-vbDouble '(0 . 2)))
           (setq SA2 (vlax-make-safearray vlax-vbDouble '(0 . 2)))
           (while (/= "SEQEND" (cdr (assoc 0 ENTLIST)))
            (setq OGLINE nil)
            (setq P1 (cdr (assoc 10 ENTLIST)))
            (setq Z1 (nth 2 P1))
            (setq OS (RFL:STAOFF P1))
            (if (/= nil OS)
             (progn
              (setq STA (car OS))
              (princ (strcat "\n" (rtos STA)))
              (setq OS1 (cadr OS))
              (setq OS2 (+ OS1 (* (RFL:SIGN OS1) (cdr (assoc "SWATH" RFL:DAYLIGHTLIST)))))
              (setq P2 (RFL:XY (list STA OS2)))
              (if (/= nil P2)
               (progn
                (setq P2 (append P2 (list Z1)))
                (setq OGLINE nil)
                (setq OGLINE (vlax-invoke-method OBSURFACE "SampleElevations" (car P1) (cadr p1) (car P2) (cadr p2)))
                (if (/= nil OGLINE)
                 (if (/= 0 (vlax-variant-type OGLINE))
                  (progn
                   (setq OGLINELIST nil)
                   (setq OGLINE (vlax-variant-value OGLINE))
                   (setq C (vlax-safearray-get-l-bound OGLINE 1))
                   (while (<= C (vlax-safearray-get-u-bound OGLINE 1))
                    (setq OGLINELIST (append OGLINELIST (list (list (vlax-safearray-get-element OGLINE C)
                                                                    (vlax-safearray-get-element OGLINE (+ C 1))
                                                                    (vlax-safearray-get-element OGLINE (+ C 2))))))
                    (setq C (+ C 3))
                   )
                   (setq C 0)
                   (setq OGOFFSETLIST nil)
                   (while (< C (length OGLINELIST))
                    (setq OGOFFSETLIST (append OGOFFSETLIST
                                               (list (list (cadr (RFL:STAOFF (nth C OGLINELIST)))
                                                           (last (nth C OGLINELIST))))))
                    (setq C (+ C 1))
                   )
                   (setq NODE nil)
                   (setq PD1 nil)
                   (setq PD2 nil)
                   (if (= "1" (cdr (assoc "USEDITCH" RFL:DAYLIGHTLIST)))
                    (if (> Z1 (cadar OGOFFSETLIST))
                     (progn
                      (GETFILLPOINT)
                      (if (<= (- Z1 (cadr P2)) (cdr (assoc "DITCHDEPTH" RFL:DAYLIGHTLIST)))
                       (progn
                        (setq Z1 (- Z1 (cdr (assoc "DITCHDEPTH" RFL:DAYLIGHTLIST))))
                        (setq PD1 (list (+ OS1 (* (RFL:SIGN OS1)
                                                  (cdr (assoc "DITCHDEPTH" RFL:DAYLIGHTLIST))
                                                  (cdr (assoc "DITCHBACK" RFL:DAYLIGHTLIST))))
                                        Z1))
                        (setq PD2 (list (+ (car PD1) (* (RFL:SIGN OS1)
                                                        (cdr (assoc "DITCHWIDTH" RFL:DAYLIGHTLIST))))
                                        Z1))
                        (setq OS1 (car PD2))
                        (setq P2 (GETSLOPEINT OS1 Z1 (* (RFL:SIGN OS1) (cdr (assoc "CS1" RFL:DAYLIGHTLIST))) OGOFFSETLIST))
                        (if (/= nil P2)
                         (progn
                          (if (>= (- (cadr P2) Z1) (cdr (assoc "CD2" RFL:DAYLIGHTLIST)))
                           (progn
                            (setq P2 (GETSLOPEINT OS1 Z1 (* (RFL:SIGN OS1) (cdr (assoc "CS3" RFL:DAYLIGHTLIST))) OGOFFSETLIST))
                           )
                          )

                          (if (< (* (RFL:SIGN OS1) (- (car P2) OS1)) 0.0)
                           (progn
                            (GETFILLPOINT)
                           )
                          )
                         )
                        )
                       )
                      )
                     )
                     (progn
                      (setq Z1 (- Z1 (cdr (assoc "DITCHDEPTH" RFL:DAYLIGHTLIST))))
                      (setq PD1 (list (+ OS1 (* (RFL:SIGN OS1)
                                                (cdr (assoc "DITCHDEPTH" RFL:DAYLIGHTLIST))
                                                (cdr (assoc "DITCHBACK" RFL:DAYLIGHTLIST))))
                                      Z1))
                      (setq PD2 (list (+ (car PD1) (* (RFL:SIGN OS1)
                                                      (cdr (assoc "DITCHWIDTH" RFL:DAYLIGHTLIST))))
                                      Z1))
                      (setq OS1 (car PD2))
                      (GETCUTPOINT)
                      (if (< (* (RFL:SIGN OS1) (- (car P2) OS1)) 0.0)
                       (progn
                         (GETFILLPOINT)
                       )
                      )
                     )
                    )
                    (if (> Z1 (cadar OGOFFSETLIST))
                     (progn
                      (GETFILLPOINT)
                     )
                     (progn
                      (GETCUTPOINT)
                     )
                    )
                   )
                   (setq CATCHLINE (append CATCHLINE (list (list STA P2 PD1 PD2))))
                  )
                 )
                )
                (setq ENT (entnext ENT))
                (setq ENTLIST (entget ENT))
               )
              )
             )
            )
           )
           (setq C 0)
           (command "._3DPOLY")
           (while (< C (length CATCHLINE))
            (setq NODE (nth C CATCHLINE))
            (setq C (+ C 1))
            (if (/= nil (setq P1 (cadr NODE)))
             (progn
              (setq P (RFL:XY (list (car NODE) (car P1))))
              (if (/= P nil)
               (progn
                (command (append P (cdr P1)))
               )
              )
             )
            )
           )
           (command)
           (setq C 0)
           (command "._3DPOLY")
           (while (< C (length CATCHLINE))
            (setq NODE (nth C CATCHLINE))
            (setq C (+ C 1))
            (if (= nil (setq P1 (caddr NODE)))
             (progn
              (command)
              (command "._3DPOLY")
             )
             (progn
              (setq P (RFL:XY (list (car NODE) (car P1))))
              (if (/= P nil)
               (progn
                (command (append P (cdr P1)))
               )
              )
             )
            )
           )
           (command)
           (setq C 0)
           (command "._3DPOLY")
           (while (< C (length CATCHLINE))
            (setq NODE (nth C CATCHLINE))
            (setq C (+ C 1))
            (if (= nil (setq P1 (cadddr NODE)))
             (progn
              (command)
              (command "._3DPOLY")
             )
             (progn
              (setq P (RFL:XY (list (car NODE) (car P1))))
              (if (/= P nil)
               (progn
                (command (append P (cdr P1)))
               )
              )
             )
            )
           )
           (command)
          )
         )
        )
       )
      )
     )
    )
   )
  )
 )

 (setvar "CMDECHO" CMDECHO)
 (setvar "OSMODE" OSMODE)
 (setvar "ANGBASE" ANGBASE)
 (setvar "ANGDIR" ANGDIR)
 (setvar "DIMZIN" DIMZIN)
)
