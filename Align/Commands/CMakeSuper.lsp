;
;
;     Program written by Robert Livingston, 2017-02-18
;
;     C:MAKESUPER is a utility for generating Superelevations along an alignment.
;
;
(defun C:MAKESUPER (/ C GETSUPER L NODE REP R R1 R2 RUNOUT S S1 S2 STA TABLE VDES)
 (defun GETSUPER (TABLE R VDES)
  (apply (read TABLE) (list R VDES))
 )
 (initget "Bc Tac")
 (if (setq REP (getkword "\n6% BC Sup or 6% TAC (BC/TAC) <TAC> : "))
  (setq TABLE REP)
  (setq TABLE "TAC")
 )
 (if (= TABLE "TAC")
  (setq TABLE "RFL:GETTACSUPER")
  (setq TABLE "RFL:GETBCSUPER")
 )
 (if (setq REP (getdist "\nDesign speed (must be table column value) <60>: "))
  (setq VDES REP)
  (setq VDES 60.0)
 )
 (if (setq REP (getdist "\nEnter spiral runout distance <60.0> : "))
  (setq RUNOUT REP)
  (setq RUNOUT 60.0)
 )
 (setq RFL:SUPERLIST nil)
 (foreach NODE RFL:ALIGNLIST
  (cond ((listp (last NODE))
         (progn ; Spiral
          (print "SPIRAL")
          (setq S nil S1 nil S2 nil)
          (setq STA (car NODE))
          (setq L (- (RFL:ARCLENGTH (nth 1 NODE) (nth 2 NODE) (nth 3 NODE)) (last (nth 3 NODE))))
          (setq R1 (RFL:GETRADIUS STA))
          (if (> (abs R1) 10000.0) (setq R1 0.0))
          (setq R2 (RFL:GETRADIUS (+ STA L)))
          (if (> (abs R2) 10000.0) (setq R2 0.0))
          (if (< (abs R1) RFL:TOL)
           (setq S1 (list -2.0 0.0))
           (setq S1 (GETSUPER TABLE (abs R1) VDES))
          )
          (if (or (< R1 0.0) (< R2 0.0)) (setq S1 (reverse S1)))
          (if (< (abs R2) RFL:TOL)
           (setq S2 (list -2.0 0.0))
           (setq S2 (GETSUPER TABLE (abs R2) VDES))
          )
          (if (or (< R1 0.0) (< R2 0.0)) (setq S2 (reverse S2)))
          (cond ((= 0.0 (car S1))
                 (setq S (list (+ STA (* L (/ 2.0 (car S2)))) 2.0 -2.0))
                )
                ((= 0.0 (cadr S1))
                 (setq S (list (+ STA (* L (/ 2.0 (cadr S2)))) -2.0 2.0))
                )
                ((= 0.0 (car S2))
                 (setq S (list (- (+ STA L) (* L (/ 2.0 (car S1)))) 2.0 -2.0))
                )
                ((= 0.0 (cadr S2))
                 (setq S (list (- (+ STA L) (* L (/ 2.0 (cadr S1)))) -2.0 2.0))
                )
          )
          (if (/= S nil)
           (progn
            (setq RFL:SUPERLIST (append RFL:SUPERLIST (list (list STA (car S1) (cadr S1)))))
            (setq RFL:SUPERLIST (append RFL:SUPERLIST (list S)))
            (setq RFL:SUPERLIST (append RFL:SUPERLIST (list (list (+ STA L) (car S2) (cadr S2)))))
           )
          )
         )
        )
        ((< (abs (last NODE)) RFL:TOL)
         (progn ; Line
          (print "LINE")
          (if (> (distance (nth 1 NODE) (nth 2 NODE)) (* 2.0 RUNOUT))
           (progn
            (if (= (car NODE) (car (car RFL:ALIGNLIST)))
             (setq RFL:SUPERLIST (append RFL:SUPERLIST (list (list (nth 0 NODE) -2.0 -2.0))))
             (setq RFL:SUPERLIST (append RFL:SUPERLIST (list (list (+ (nth 0 NODE) RUNOUT) -2.0 -2.0))))
            )
            (if (= (car NODE) (car (last RFL:ALIGNLIST)))
             (setq RFL:SUPERLIST (append RFL:SUPERLIST (list (list (+ (nth 0 NODE) (distance (nth 1 NODE) (nth 2 NODE))) -2.0 -2.0))))
             (setq RFL:SUPERLIST (append RFL:SUPERLIST (list (list (- (+ (nth 0 NODE) (distance (nth 1 NODE) (nth 2 NODE))) RUNOUT) -2.0 -2.0))))
            )
           )
          )
         )
        )
        (T
         (progn ; Arc
          (print "ARC")
          (setq S (GETSUPER TABLE (RFL:RADIUS (nth 1 NODE) (nth 2 NODE) (abs (nth 3 NODE))) VDES))
          (if (< (nth 3 NODE) 0.0)
           (setq S (reverse S))
          )
          (setq RFL:SUPERLIST (append RFL:SUPERLIST (list (list (nth 0 NODE) (car S) (cadr S)))))
          (setq RFL:SUPERLIST (append RFL:SUPERLIST (list (list (+ (nth 0 NODE) (RFL:ARCLENGTH (nth 1 NODE) (nth 2 NODE) (nth 3 NODE))) (car S) (cadr S)))))
         )
        )
  )
 )
 (setq S RFL:SUPERLIST)
 (setq RFL:SUPERLIST (list (car S)))
 (setq C 1)
 (while (< C (length S))
  (if (> (abs (- (car (nth C S)) (car (nth (1- C) S)))) RFL:TOL)
   (setq RFL:SUPERLIST (append RFL:SUPERLIST (list (nth C S))))
   (if (and (or (= (cadr (nth C S)) 0.0) (= (cadr (nth C S)) -2.0))
            (or (= (caddr (nth C S)) 0.0) (= (caddr (nth C S)) -2.0))
       )
    (progn
     (setq RFL:SUPERLIST (reverse (cdr (reverse RFL:SUPERLIST))))
     (setq RFL:SUPERLIST (append RFL:SUPERLIST (list (list (car (nth C S)) 0.0 0.0))))
    )
   )
  )
  (setq C (1+ C))
 )
)
