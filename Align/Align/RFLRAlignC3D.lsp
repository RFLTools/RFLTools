;
;
;     Program written by Robert Livingston, 2021-12-01
;
;     RFL:RALIGNC3D reads an OBALIGNMENT object to RFL:ALIGNLIST
;
;
(defun RFL:RALIGNC3D (OBALIGNMENT / ALSAVE C CMAX E1 E2 ENT ENTITY ENTLIST NODE OBALIGNMENT OBENTITIES SETARC SETSPIRAL SETTANGENT SPIRALENTITY STA STALIST)
 (defun SETTANGENT (ENTITY / P1 P2)
  (setq P1 (list (vlax-get-property ENTITY "StartEasting")
                 (vlax-get-property ENTITY "StartNorthing")
           )
  )
  (setq P2 (list (vlax-get-property ENTITY "EndEasting")
                 (vlax-get-property ENTITY "EndNorthing")
           )
  )
  (setq RFL:ALIGNLIST (append RFL:ALIGNLIST (list (list (vlax-get-property ENTITY "StartingStation") P1 P2 0.0))))
 )

 (defun SETARC (ENTITY / P1 P2 PC CCW R ANG BULGE)
  (setq P1 (list (vlax-get-property ENTITY "StartEasting")
                 (vlax-get-property ENTITY "StartNorthing")
           )
  )
  (setq P2 (list (vlax-get-property ENTITY "EndEasting")
                 (vlax-get-property ENTITY "EndNorthing")
           )
  )
  (setq PC (list (vlax-get-property ENTITY "CenterEasting")
                 (vlax-get-property ENTITY "CenterNorthing")
           )
  )
  (setq CCW (vlax-get-property ENTITY "Clockwise"))
  (setq R (vlax-get-property ENTITY "Radius"))
  (setq ANG (vlax-get-property ENTITY "Delta"))
  (setq BULGE (RFL:TAN (/ ANG 4.0)))
  (if (= :vlax-true CCW) (setq BULGE (* -1.0 BULGE)))
  (setq RFL:ALIGNLIST (append RFL:ALIGNLIST (list (list (vlax-get-property ENTITY "StartingStation") P1 P2 BULGE))))
 )

 (defun SETSPIRAL (ENTITY / A ANG BULGE L0 LT P1 P2 PLTST PINT PST RIN ROUT ST THETA TMP X Y)
  (setq RIN (vlax-get-property ENTITY "RadiusIn"))
  (setq ROUT (vlax-get-property ENTITY "RadiusOut"))
  (setq TMP (/ 1.0 (max RIN ROUT)))
  ;(setq TMP (vlax-get-property ENTITY "Compound"))
  ;(if (= TMP :vlax-false)
  (if (< TMP RFL:TOL)
   (progn
    (setq P1 (list (vlax-get-property ENTITY "StartEasting")
                   (vlax-get-property ENTITY "StartNorthing")
             )
    )
    (setq P2 (list (vlax-get-property ENTITY "EndEasting")
                   (vlax-get-property ENTITY "EndNorthing")
             )
    )
    (setq PLTST (list (vlax-get-property ENTITY "SPIEasting")
                      (vlax-get-property ENTITY "SPINorthing")
                )
    )
    (setq LO 0.0)
    (if (< (distance P2 PLTST) (distance P1 PLTST))
     (setq PLT P1 PST P2)
     (setq PLT P2 PST P1)
    )
    (setq BULGE (list PLT PLTST PST LO))
    (setq RFL:ALIGNLIST (append RFL:ALIGNLIST (list (list (vlax-get-property ENTITY "StartingStation") P1 P2 BULGE))))
   )
   (progn
    (setq P1 (list (vlax-get-property ENTITY "StartEasting")
                   (vlax-get-property ENTITY "StartNorthing")
             )
    )
    (setq P2 (list (vlax-get-property ENTITY "EndEasting")
                   (vlax-get-property ENTITY "EndNorthing")
             )
    )
    (setq PINT (list (vlax-get-property ENTITY "SPIEasting")
                     (vlax-get-property ENTITY "SPINorthing")
               )
    )
    (setq RIN (vlax-get-property ENTITY "RadiusIn"))
    (setq ROUT (vlax-get-property ENTITY "RadiusOut"))
    (setq A (vlax-get-property ENTITY "A"))
    (if (< RIN ROUT)
     (progn
      (setq THETA (/ (* A A) (* 2.0 RIN RIN)))
      (setq PST P1)
      ;(setq LO (- (/ (* A A) RIN) (vlax-get-property ENTITY "Length")))
      (setq LO (/ (* A A) ROUT))
      (setq ANG (angle PST PINT))
      (setq X (* RIN (RFL:SPIRALFXR THETA)))
      (setq Y (* RIN (RFL:SPIRALFYR THETA)))
      (setq ST (/ Y (sin THETA)))
      (setq LT (- X (/ Y (RFL:TAN THETA))))
      (setq PLTST (list (+ (car PST) (* ST (cos ANG)))
                        (+ (cadr PST) (* ST (sin ANG)))))
      (if (> (sin (- (angle PINT P2) (angle P1 PINT))) 0.0)
       (setq ANG (+ ANG THETA))
       (setq ANG (- ANG THETA))
      )
      (setq PLT (list (+ (car PLTST) (* LT (cos ANG)))
                      (+ (cadr PLTST) (* LT (sin ANG)))))
     )
     (progn
      (setq THETA (/ (* A A) (* 2.0 ROUT ROUT)))
      (setq PST P2)
      ;(setq LO (- (/ (* A A) ROUT) (vlax-get-property ENTITY "Length")))
      (setq LO (/ (* A A) RIN))
      (setq ANG (angle PST PINT))
      (setq X (* ROUT (RFL:SPIRALFXR THETA)))
      (setq Y (* ROUT (RFL:SPIRALFYR THETA)))
      (setq ST (/ Y (sin THETA)))
      (setq LT (- X (/ Y (RFL:TAN THETA))))
      (setq PLTST (list (+ (car PST) (* ST (cos ANG)))
                        (+ (cadr PST) (* ST (sin ANG)))))
      (if (> (sin (- (angle PINT P1) (angle P2 PINT))) 0.0)
       (setq ANG (+ ANG THETA))
       (setq ANG (- ANG THETA))
      )
      (setq PLT (list (+ (car PLTST) (* LT (cos ANG)))
                      (+ (cadr PLTST) (* LT (sin ANG)))))
     )
    )
    (setq BULGE (list PLT PLTST PST LO))
    (setq RFL:ALIGNLIST (append RFL:ALIGNLIST (list (list (vlax-get-property ENTITY "StartingStation") P1 P2 BULGE))))
   )
  )
 )

 (if OBALIGNMENT
  (progn
   (setq RFL:ALIGNLIST nil)
   (setq OBENTITIES (vlax-get-property OBALIGNMENT "Entities"))
   (setq CMAX (vlax-get-property OBENTITIES "Count"))
   (setq C 0)
   (while (< C CMAX)
    (setq ENTITY (vlax-invoke-method OBENTITIES "Item" C))
    (cond
     ((= 1 (vlax-get-property ENTITY "Type"))
      (progn
       (SETTANGENT ENTITY)
      )
     )
     ((= 2 (vlax-get-property ENTITY "Type"))
      (progn
       (SETARC ENTITY)
      )
     )
     ((= 3 (vlax-get-property ENTITY "Type"))
      (progn
       (SETSPIRAL ENTITY)
      )
     )
     ((= 4 (vlax-get-property ENTITY "Type"))
      (progn
       (SETSPIRAL (vlax-get-property ENTITY "SpiralIn"))
       (SETARC (vlax-get-property ENTITY "Arc"))
       (SETSPIRAL (vlax-get-property ENTITY "SpiralOut"))
      )
     )
     ((= 8 (vlax-get-property ENTITY "Type"))
      (progn
       (SETSPIRAL (vlax-get-property ENTITY "SpiralIn"))
       (SETARC (vlax-get-property ENTITY "ArcOut"))
      )
     )
     ((= 9 (vlax-get-property ENTITY "Type"))
      (progn
       (SETARC (vlax-get-property ENTITY "ArcIn"))
       (SETSPIRAL (vlax-get-property ENTITY "SpiralOut"))
      )
     )
     ((= 12 (vlax-get-property ENTITY "Type"))
      (progn
       (SETSPIRAL (vlax-get-property ENTITY "Spiral1"))
       (SETARC (vlax-get-property ENTITY "Arc1"))
       (SETSPIRAL (vlax-get-property ENTITY "Spiral2"))
       (SETARC (vlax-get-property ENTITY "Arc2"))
       (SETSPIRAL (vlax-get-property ENTITY "Spiral3"))
      )
     )
    )
    (setq C (1+ C))
   )
  )
  nil
 )

 (setq ALSAVE RFL:ALIGNLIST RFL:ALIGNLIST nil)
 (if (/= nil ALSAVE)
  (progn
   (setq STALIST nil)
   (foreach NODE ALSAVE
    (setq STALIST (append STALIST (list (car NODE))))
   )
   (setq STALIST (vl-sort STALIST '<))
   (foreach STA STALIST
    (setq RFL:ALIGNLIST (append RFL:ALIGNLIST (list (assoc STA ALSAVE))))
   )
  )
 )

 nil
)
