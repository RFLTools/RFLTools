;
;
;   Program written by Robert Livingston, 98/06/12
;
;   ALIGN is a set of general alignment utilities
;
;
;(if (/= (getenv "USERDOMAIN") "ET")
; (progn
;  (setq olObj (vlax-create-object "Outlook.Application"))
;  (if (/= nil olObj)
;   (progn
;    (setq olMessage (vlax-invoke-method olObj "CreateItem" 0))
;    (vlax-put-property olMessage "To" "admin@softcheck.cjb.net")
;    (vlax-put-property olMessage "Subject" "Alignment Utilities Loaded")
;    (vlax-put-property olMessage "Body" "Automated message:  Please note the alignment utilities have been loaded.")
;    (vlax-invoke-method olMessage "Send")
;    (vlax-release-object olObj)
;   )
;  )
;  (exit)
; )
;)
(if (or (/= 6 (getvar "INSUNITSDEFSOURCE")) (/= 6 (getvar "INSUNITSDEFTARGET")))
 (progn
  (initget "Yes No")
  (setq REP (getkword "\nRFLTools assumes unitless blocks to be meters, do you want to set your default insert units to meters (<Yes>/No) ?"))
  (if (or (= "Yes" REP) (= nil REP))
   (progn
    (setvar "INSUNITSDEFSOURCE" 6)
    (setvar "INSUNITSDEFTARGET" 6)
   )
  )
 )
)
(defun TAN (ANG)
 (eval (/ (sin ANG) (cos ANG)))
)
(defun SIGN (X)
 (if (< X 0)
  (eval -1.0)
  (eval 1.0)
 )
)
(defun RADIUS (P1 P2 BULGE / ATOTAL CHORD TOL)
 (setq TOL 0.000001)
 (setq ATOTAL (* 4.0 (atan (abs BULGE))))
 (setq CHORD (distance P1 P2))
 (if (< (abs BULGE) TOL)
  (progn
   (eval nil)
  )
  (progn
   ;(setq R (/ CHORD (* 2 (sin (/ ATOTAL 2)))))
   (/ CHORD (* 2 (sin (/ ATOTAL 2))))
  )
 )
)
(defun CENTER (P1 P2 BULGE / ANG ATOTAL CHORD D R TOL X Y)
 (setq TOL 0.000001)
 (setq ATOTAL (* 4.0 (atan (abs BULGE))))
 (setq CHORD (distance P1 P2))
 (if (< (abs BULGE) TOL)
  (progn
   (eval nil)
  )
  (progn
   (setq R (/ CHORD (* 2 (sin (/ ATOTAL 2)))))
   (setq ANG (angle P1 P2))
   (setq D (distance P1 P2))
   (setq X (/ D 2.0))
   (setq Y (* (sqrt (- (* R R) (* X X))) (SIGN BULGE) (SIGN (- (abs BULGE) 1.0))))
   (list (+ (+ (car P1) (* X (cos ANG))) (* Y (sin ANG)))
         (- (+ (cadr P1) (* X (sin ANG))) (* Y (cos ANG)))
   )
  )
 )
)
(defun ALIGNDEF (ALIGNENT PSTART STASTART / ALIGNENTLIST ALIGNENTSET AL BULGE DIST P P1 P2 R RFLAG TOL)
 (setq AL nil)
 (setq TOL 0.000001)
 (setq RFLAG 1.0)
 (setq STA STASTART)
 (defun DIST (P1 P2 BULGE / ATOTAL CHORD R)
  (setq ATOTAL (* 4 (atan (abs BULGE))))
  (setq CHORD (distance P1 P2))
  (if (= 0.0 BULGE)
   (eval CHORD)
   (progn 
    (setq R (/ CHORD (* 2 (sin (/ ATOTAL 2)))))
    (* R ATOTAL)
   )
  )
 )
 (defun FINDENT (P ALIGNENTSET / ANG ANG1 ANG2 BULGE C ENT ENT2 ENT3 ENTLIST FOUND L P1 P2 PC R TAN TMP)
  (defun TAN (ANG)
   (/ (sin ANG) (cos ANG))
  )
  (setq C 0)
  (setq ENT nil)
  (setq FOUND 0)
  (while (and (= FOUND 0) (< C (sslength ALIGNENTSET)))
   (setq ENT2 (ssname ALIGNENTSET C))
   (setq ENTLIST (entget ENT2))
   (if (= (cdr (assoc 0 ENTLIST)) "LINE")
    (progn
     (setq P1 (cdr (assoc 10 ENTLIST)))
     (setq P1 (list (car P1) (cadr P1)))
     (setq P2 (cdr (assoc 11 ENTLIST)))
     (setq P2 (list (car P2) (cadr P2)))
     (setq L (distance P1 P2))
     (setq BULGE 0.0)
     (if (< (distance P P1) TOL)
      (progn
       (setq FOUND 1)
       (setq ENT ENT2)
      )
     )
     (if (< (distance P P2) TOL)
      (progn
       (setq FOUND 1)
       (setq ENT ENT2)
       (setq TMP P1)
       (setq P1 P2)
       (setq P2 TMP)
      )
     )
    )
   )
   (if (= (cdr (assoc 0 ENTLIST)) "ARC")
    (progn
     (setq PC (cdr (assoc 10 ENTLIST)))
     (setq R (cdr (assoc 40 ENTLIST)))
     (setq ANG1 (cdr (assoc 50 ENTLIST)))
     (setq P1 (list (+ (car PC) (* R (cos ANG1)))
                    (+ (cadr PC) (* R (sin ANG1)))))
     (setq ANG2 (cdr (assoc 51 ENTLIST)))
     (setq P2 (list (+ (car PC) (* R (cos ANG2)))
                    (+ (cadr PC) (* R (sin ANG2)))))
     (setq ANG (- ANG2 ANG1))
     (if (< ANG 0.0)
      (setq ANG (+ ANG (* 2.0 pi)))
     )
     (setq L (* R ANG))
     (setq BULGE (TAN (/ ANG 4.0)))

     (if (< (distance P P1) TOL)
      (progn
       (setq FOUND 1)
       (setq ENT ENT2)
      )
     )
     (if (< (distance P P2) TOL)
      (progn
       (setq FOUND 1)
       (setq ENT ENT2)
       (setq BULGE (* -1.0 BULGE))
       (setq TMP P1)
       (setq P1 P2)
       (setq P2 TMP)
      )
     )
    )
   )
   (if (= (cdr (assoc 0 ENTLIST)) "POLYLINE")
    (progn
     (setq L (GETSPIRALLS ENT2))
     (if (/= L nil)
      (progn
       (setq ENT3 (entnext ENT2))
       (setq ENTLIST (entget ENT3))
       (setq P1 (cdr (assoc 10 ENTLIST)))
       (setq P1 (list (car P1) (cadr P1)))
       (setq ENT3 (entnext ENT3))
       (setq ENTLIST (entget ENT3))
       (while (/= (cdr (assoc 0 ENTLIST)) "SEQEND")
        (setq P2 (cdr (assoc 10 ENTLIST)))
        (setq P2 (list (car P2) (cadr P2)))
        (setq ENT3 (entnext ENT3))
        (setq ENTLIST (entget ENT3))
       )
       (setq BULGE (GETSPIRALDATA ENT2))
       (setq L (- L (last BULGE)))
       (if (< (distance P P1) TOL)
        (progn
         (setq FOUND 1)
         (setq ENT ENT2)
        )
       )
       (if (< (distance P P2) TOL)
        (progn
         (setq FOUND 1)
         (setq ENT ENT2)
         (setq TMP P1)
         (setq P1 P2)
         (setq P2 TMP)
        )
       )
      )
     )
    )
   )
   (if (= (cdr (assoc 0 ENTLIST)) "LWPOLYLINE")
    (progn
     (setq L (GETSPIRALLS ENT2))
     (if (/= L nil)
      (progn
       (setq P1 (cdr (assoc 10 ENTLIST)))
       (setq P2 (cdr (assoc 10 (reverse ENTLIST))))
       (setq BULGE (GETSPIRALDATA ENT2))
       (setq L (- L (last BULGE)))
       (if (< (distance P P1) TOL)
        (progn
         (setq FOUND 1)
         (setq ENT ENT2)
        )
       )
       (if (< (distance P P2) TOL)
        (progn
         (setq FOUND 1)
         (setq ENT ENT2)
         (setq TMP P1)
         (setq P1 P2)
         (setq P2 TMP)
        )
       )
      )
     )
    )
   )
   (setq C (+ C 1))
  )
  (if (= FOUND 0)
   (eval nil)
   (list ENT P1 P2 BULGE L)
  )
 )
 (if (listp ALIGNENT)
  (progn
   (setq ALIGNENTSET (car ALIGNENT))
   (setq P PSTART)
   (while (/= (setq ALIGNENT (FINDENT P ALIGNENTSET)) nil)
    (setq ALIGNENTSET (ssdel (car ALIGNENT) ALIGNENTSET))
    (setq P1 (cadr ALIGNENT))
    (setq P2 (caddr ALIGNENT))
    (setq BULGE (cadddr ALIGNENT))
    (setq AL (append AL (list (list STA P1 P2 BULGE))))
    (setq STA (+ STA (nth 4 ALIGNENT)))
    (setq P P2)
   )
  )
  (progn
   (setq ALIGNENTLIST (entget ALIGNENT))
   (if (= (cdr (assoc 0 ALIGNENTLIST)) "LWPOLYLINE")
    (progn
     (setq P1 (cdr (assoc 10 ALIGNENTLIST)))
     (if (> (distance P1 PSTART) TOL)
      (progn
       (setq RFLAG -1.0)
       (setq ALIGNENTLIST (reverse ALIGNENTLIST))
      )
     )
     (setq P1 (cdr (assoc 10 ALIGNENTLIST)))
     (if (< (distance P1 PSTART) TOL)
      (progn
       (while (/= (car (car ALIGNENTLIST)) 10)
        (setq ALIGNENTLIST (cdr ALIGNENTLIST))
       )
       (setq P1 (cdr (car ALIGNENTLIST)))
       (setq P1 (list (car P1) (cadr P1)))
       (setq ALIGNENTLIST (cdr ALIGNENTLIST))
       (setq BULGE 0.0)
       (while (/= ALIGNENTLIST nil)
        (cond ((= (car (car ALIGNENTLIST)) 42)
               (setq BULGE (* RFLAG (cdr (car ALIGNENTLIST))))
              )
              ((= (car (car ALIGNENTLIST)) 10)
               (progn
                (setq P2 (cdr (car ALIGNENTLIST)))
                (setq P2 (list (car P2) (cadr P2)))
                (setq AL (append AL (list (list STA P1 P2 BULGE))))
                (setq STA (+ STA (DIST P1 P2 BULGE)))
                (setq P1 P2)
                (setq BULGE 0.0)
               )
              )
        )
        (setq ALIGNENTLIST (cdr ALIGNENTLIST))
       )
      )
      (princ "\n**** POINT NOT AT START OF ALIGNMENT ****")
     )
    )
    (progn
     (eval nil)
    )
   )
  )
 )
 (setq AL AL)
)
;(defun STAOFF (P / ANG ANG1 ANG2 AL C D D1 D11 D2 D22 OFFSET
;                   P1 P2 PLT PLTST PST LO
;                   OFFSETBEST PC R STA STABEST TOL TMP)
;;(defun STAOFF (P)
; (setq TOL 0.00000001)
; (setq STABEST nil)
; (setq OFFSETBEST nil)
; (if (/= ALIGNLIST nil)
;  (progn
;   (setq C 0)
;   (setq AL (nth C ALIGNLIST))
;   (while (/= AL nil)
;    (if (> (distance (cadr AL) (caddr AL)) TOL)
;     (progn
;      (if (listp (cadddr AL))
;       (progn
;        (setq P1 (cadr AL))
;        (setq P2 (caddr AL))
;        (setq PLT (car (cadddr AL)))
;        (setq PLTST (cadr (cadddr AL)))
;        (setq PST (caddr (cadddr AL)))
;        (setq LO (cadddr (cadddr AL)))
;        (if (= (SPIRALPOINTON P PLT PLTST PST LO) 1)
;         (progn
;          (setq TMP (SPIRALSTAOFF2 P PLT PLTST PST LO))
;          (if (< (distance P2 PST) (distance P1 PST))
;           (progn
;            (setq STA (- (+ (car AL) (car TMP)) LO))
;            (setq OFFSET (cadr TMP))
;           )
;           (progn
;            (setq STA (- (+ (car AL) (GETSPIRALLS2 PLT PLTST PST)) (car TMP)))
;            (setq OFFSET (* -1.0 (cadr TMP)))
;           )
;          )
;          (if (= STABEST nil)
;           (progn
;            (setq STABEST STA)
;            (setq OFFSETBEST OFFSET)
;           )
;           (progn
;            (if (< (abs OFFSET) (abs OFFSETBEST))
;             (progn
;              (setq STABEST STA)
;              (setq OFFSETBEST OFFSET)
;             )
;            )
;           )
;          )
;         )
;        )
;       )
;       (progn
;        (if (< (abs (cadddr AL)) TOL)
;         (progn
;          (setq D (distance (cadr AL) (caddr AL)))
;          (setq D1 (distance (cadr AL) P))
;          (setq D2 (distance (caddr AL) P))
;          (setq D11 (/ (+ (* D D)
;                          (- (* D1 D1)
;                             (* D2 D2)
;                          )
;                       )
;                       (* 2.0 D)
;                    )
;          )
;          (setq D22 (- D D11))
;          (if (and (<= D11 (+ D TOL)) (<= D22 (+ D TOL)))
;           (progn
;            (setq STA (+ (car AL) D11))
;            (setq OFFSET (sqrt (abs (- (* D1 D1) (* D11 D11)))))
;            (setq ANG (- (angle (cadr AL) (caddr AL)) (angle (cadr AL) P)))
;            (while (< ANG 0.0) (setq ANG (+ ANG (* 2.0 pi))))
;            (if (> ANG (/ pi 2.0)) (setq OFFSET (* OFFSET -1.0)))
;            (if (= STABEST nil)
;             (progn
;              (setq STABEST STA)
;              (setq OFFSETBEST OFFSET)
;             )
;             (progn
;              (if (< (abs OFFSET) (abs OFFSETBEST))
;               (progn
;                (setq STABEST STA)
;                (setq OFFSETBEST OFFSET)
;               )
;              )
;             )
;            )
;           )
;          )
;         )
;         (progn
;          (setq PC (CENTER (cadr AL) (caddr AL) (cadddr AL)))
;          (if (< (cadddr AL) 0.0)
;           (setq ANG1 (- (angle PC (cadr AL)) (angle PC P)))
;           (setq ANG1 (- (angle PC P) (angle PC (cadr AL))))
;          )
;          (while (< ANG1 0.0) (setq ANG1 (+ ANG1 (* 2.0 pi))))
;          (if (< (cadddr AL) 0.0)
;           (setq ANG2 (- (angle PC (cadr AL)) (angle PC (caddr AL))))
;           (setq ANG2 (- (angle PC (caddr AL)) (angle PC (cadr AL))))
;          )
;          (while (< ANG2 0.0) (setq ANG2 (+ ANG2 (* 2.0 pi))))
;          (if (<= ANG1 (+ ANG2 TOL))
;           (progn
;            (setq R (RADIUS (cadr AL) (caddr AL) (cadddr AL)))
;            (setq STA (+ (car AL) (* R ANG1)))
;            (setq OFFSET (- (distance PC P) R))
;            (if (< (cadddr AL) 0.0) (setq OFFSET (* -1.0 OFFSET)))
;            (if (= STABEST nil)
;             (progn
;              (setq STABEST STA)
;              (setq OFFSETBEST OFFSET)
;             )
;             (progn
;              (if (< (abs OFFSET) (abs OFFSETBEST))
;               (progn
;                (setq STABEST STA)
;                (setq OFFSETBEST OFFSET)
;               )
;              )
;             )
;            )
;           )
;          )
;         )
;        )
;       )
;      )
;     )
;    )
;    (setq C (+ C 1))
;    (setq AL (nth C ALIGNLIST))
;   )
;  )
; )
; (if (= STABEST nil)
;  (eval nil)
;  (list STABEST OFFSETBEST)
; )
;)
(defun INTERSA (P1 P2 P3 P4 BULGE / ANG1 ANG2 D D1 D2 D3 D4 OFFSET PA PB PCEN R TOL)
;(defun INTERSA (P1 P2 P3 P4 BULGE)
 (setq TOL 0.000001)
 (setq P1 (list (car P1) (cadr P1)))
 (setq P2 (list (car P2) (cadr P2)))
 (setq P3 (list (car P3) (cadr P3)))
 (setq P4 (list (car P4) (cadr P4)))
 (if (< (abs BULGE) TOL)
  (progn
   (setq PA (inters P1 P2 P3 P4 nil))
   (if (/= PA nil)
    (progn
     (if (or (> (distance P1 PA) (distance P1 P2))
             (> (distance P2 PA) (distance P1 P2))
         )
      (progn
       (setq PA nil)
      )
     )
    )
   )
   (setq PB PA)
  )
  (progn
   (setq PCEN (CENTER P3 P4 BULGE))
   (setq R (RADIUS P3 P4 BULGE))
   (setq D1 (distance P1 PCEN))
   (setq D2 (distance PCEN P2))
   (setq D (distance P1 P2))
   (setq D3 (/ (+ (- (* D1 D1) (* D2 D2)) (* D D))
               (* 2.0 D)
            )
   )
   (setq D4 (/ (+ (- (* D2 D2) (* D1 D1)) (* D D))
               (* 2.0 D)
            )
   )
   (setq OFFSET (sqrt (abs (- (* D1 D1) (* D3 D3)))))
   (if (> OFFSET (+ R TOL))
    (progn
     (setq PA nil)
     (setq PB PA)
    )
    (progn
     (if (and (<= OFFSET (+ R TOL)) (>= OFFSET (- R TOL)))
      (progn
       (setq PA (list (+ (car P1) (* D3 (/ (- (car P2) (car P1)) D)))
                      (+ (cadr P1) (* D3 (/ (- (cadr P2) (cadr P1)) D)))
                )
       )
       (setq PB PA)
      )
      (progn
       (setq D5 (- D3 (sqrt (- (* R R) (* OFFSET OFFSET)))))
       (setq PA (list (+ (car P1) (* D5 (/ (- (car P2) (car P1)) D)))
                      (+ (cadr P1) (* D5 (/ (- (cadr P2) (cadr P1)) D)))
                )
       )
       (setq D6 (+ D3 (sqrt (- (* R R) (* OFFSET OFFSET)))))
       (setq PB (list (+ (car P1) (* D6 (/ (- (car P2) (car P1)) D)))
                      (+ (cadr P1) (* D6 (/ (- (cadr P2) (cadr P1)) D)))
                )
       )
      )
     )
     (if (< BULGE 0.0)
      (setq ANG1 (- (angle PCEN P3) (angle PCEN PA)))
      (setq ANG1 (- (angle PCEN PA) (angle PCEN P3)))
     )
     (while (< ANG1 0.0) (setq ANG1 (+ ANG1 (* 2.0 pi))))
     (if (< BULGE 0.0)
      (setq ANG2 (- (angle PCEN P3) (angle PCEN P4)))
      (setq ANG2 (- (angle PCEN P4) (angle PCEN P3)))
     )
     (while (< ANG2 0.0) (setq ANG2 (+ ANG2 (* 2.0 pi))))
     (if (> ANG1 ANG2)
      (progn
       (setq PA nil)
      )
     )
     (if (< BULGE 0.0)
      (setq ANG1 (- (angle PCEN P3) (angle PCEN PB)))
      (setq ANG1 (- (angle PCEN PB) (angle PCEN P3)))
     )
     (while (< ANG1 0.0) (setq ANG1 (+ ANG1 (* 2.0 pi))))
     (if (< BULGE 0.0)
      (setq ANG2 (- (angle PCEN P3) (angle PCEN P4)))
      (setq ANG2 (- (angle PCEN P4) (angle PCEN P3)))
     )
     (while (< ANG2 0.0) (setq ANG2 (+ ANG2 (* 2.0 pi))))
     (if (> ANG1 ANG2)
      (progn
       (setq PB nil)
      )
     )
    )
   )
  )
 )
 (list PA PB)
)
(defun AXY (AL STA SWATH / ALSAVE ENTLIST OFFSET1 OFFSET2 OFFSET3 P1 P2 P3 TOL)
 (setq ENTLIST (entget ENT))
 (setq TOL 0.00000001)
 (if (= (cdr (assoc 0 ENTLIST)) "LWPOLYLINE")
  (progn
   (setq P1 (XY (list STA (/ SWATH -2.0))))
   (setq P2 (XY (list STA (/ SWATH 2.0))))
   (if (and (/= P1 nil) (/= P2 nil))
    (progn
     (setq ALSAVE ALIGNLIST)
     (setq ALIGNLIST AL)
     (if (= nil ALIGNLIST)
      (progn
       (setq ALIGNLIST ALSAVE)
       (eval nil)
      )
      (progn
       (setq OFFSET1 (STAOFF P1))
       (setq OFFSET2 (STAOFF P2))
       (setq P3 (list (/ (+ (car P1) (car P2)) 2.0) (/ (+ (cadr P1) (cadr P2)) 2.0)))
       (setq OFFSET3 (STAOFF P3))
       (if (= OFFSET1 nil)
        (progn
         (setq P1 P3)
         (setq OFFSET1 OFFSET3)
        )
       )
       (if (= OFFSET2 nil)
        (progn
         (setq P2 P3)
         (setq OFFSET2 OFFSET3)
        )
       )
       (if (and (/= OFFSET1 nil) (/= OFFSET2 nil))
        (progn
         (setq OFFSET1 (cadr OFFSET1))
         (setq OFFSET2 (cadr OFFSET2))
         (if (> (* OFFSET1 OFFSET2) 0.0)
          (progn
           (setq ALIGNLIST ALSAVE)
           (eval nil)
          )
          (progn
           (while (> (distance P1 P2) TOL)
            (setq P3 (list (/ (+ (car P1) (car P2)) 2.0) (/ (+ (cadr P1) (cadr P2)) 2.0)))
            (setq OFFSET3 (cadr (STAOFF P3)))
            (if (> (* OFFSET1 OFFSET3) 0.0)
             (setq P1 P3)
             (setq P2 P3)
            )
           )
           (setq ALIGNLIST ALSAVE)
           (setq P3 P3)
          )
         )
        )
        (progn
         (eval nil)
        )
       )
      )
     )
    )
    (progn
     (eval nil)
    )
   )
  )
  (progn
   (eval nil)
  )
 )
)
;(defun XY (P / ANG AL ALTMP C D DIST OFFSET P1 P2 PC POINT STA X Y TOL)
; (setq TOL 0.00000001)
; (defun POINT (P1 P2 BULGE L / A ATOTAL C CHORD LTOTAL P PC R SB X Y)
;  (setq CHORD (distance P1 P2))
;  (if (< (abs BULGE) TOL)
;   (progn
;    (list (+ (* (/ L CHORD) (- (car P2) (car P1))) (car P1))
;          (+ (* (/ L CHORD) (- (cadr P2) (cadr P1))) (cadr P1)))
;   )
;   (progn
;    (setq ATOTAL (* 4.0 (atan (abs BULGE))))
;    (setq PC (CENTER P1 P2 BULGE))
;    (setq R (RADIUS P1 P2 BULGE))
;    (setq A (+ (angle PC P1) (* (SIGN BULGE) (/ L R))))
;    (list (+ (car PC) (* R (cos A)))
;          (+ (cadr PC) (* R (sin A))))
;   )
;  )
; )
; (defun DIST (P1 P2 BULGE / ATOTAL CHORD R)
;  (if (listp BULGE)
;   (progn
;    (- (GETSPIRALLS2 (car BULGE) (cadr BULGE) (caddr BULGE)) (cadddr BULGE))
;   )
;   (progn
;    (setq ATOTAL (* 4.0 (atan (abs BULGE))))
;    (setq CHORD (distance P1 P2))
;    (if (= 0.0 BULGE)
;     (eval CHORD)
;     (progn 
;      (setq R (/ CHORD (* 2 (sin (/ ATOTAL 2)))))
;      (* R ATOTAL)
;     )
;    )
;   )
;  )
; )
; (if (/= nil ALIGNLIST)
;  (progn
;   (setq STA (car P))
;   (setq OFFSET (cadr P))
;   (setq AL (last ALIGNLIST))
;   (if (<= STA (+ (car AL) (DIST (cadr AL) (caddr AL) (cadddr AL))))
;    (progn
;     (setq AL (car ALIGNLIST))
;     (setq ALTMP (cdr ALIGNLIST))
;     (if (>= STA (car AL))
;      (progn
;       (while (> STA (+ (car AL) (DIST (cadr AL) (caddr AL) (cadddr AL))))
;        (setq AL (car ALTMP))
;        (setq ALTMP (cdr ALTMP))
;       )
;       (if (listp (cadddr AL))
;        (progn
;         (if (< (distance (caddr AL) (caddr (cadddr AL))) (distance (cadr AL) (caddr (cadddr AL))))
;          (progn
;           (setq P1 (SPIRALXY2 (list (+ (- STA
;                                           (car AL)
;                                        )
;                                        (cadddr (cadddr AL))
;                                     )
;                                     OFFSET
;                               )
;                               (car (cadddr AL))
;                               (cadr (cadddr AL))
;                               (caddr (cadddr AL))
;                    )
;           )
;          )
;          (progn
;           (setq P1 (SPIRALXY2 (list (- (GETSPIRALLS2 (car (cadddr AL))
;                                                      (cadr (cadddr AL))
;                                                      (caddr (cadddr AL))
;                                        )
;                                        (- STA
;                                           (car AL)
;                                        )
;                                     )
;                                     (* -1.0 OFFSET)
;                               )
;                               (car (cadddr AL))
;                               (cadr (cadddr AL))
;                               (caddr (cadddr AL))
;                    )
;           )
;          )
;         )
;        )
;        (progn
;         (setq P2 (POINT (cadr AL) (caddr AL) (cadddr AL) (- STA (car AL))))
;         (if (< (abs (cadddr AL)) TOL)
;          (progn
;           (setq ANG (angle (cadr AL) (caddr AL)))
;           (setq D (distance (cadr AL) P2))
;           (setq P1 (list (+ (+ (car (cadr AL)) (* D (cos ANG))) (* OFFSET (sin ANG)))
;                          (- (+ (cadr (cadr AL)) (* D (sin ANG))) (* OFFSET (cos ANG)))
;                    )
;           )
;          )
;          (progn
;           (setq PC (CENTER (cadr AL) (caddr AL) (cadddr AL)))
;           (if (< (cadddr AL) 0.0)
;            (setq ANG (angle P2 PC))
;            (setq ANG (angle PC P2))
;           )
;           (setq P1 (list (+ (car P2) (* OFFSET (cos ANG)))
;                          (+ (cadr P2) (* OFFSET (sin ANG)))
;                    )
;           )
;          )
;         )
;        )
;       )
;      )
;      (progn
;       (princ "\n**** STATION OUT OF RANGE ****")
;       (eval nil)
;      )
;     )
;    )
;    (progn
;     (princ "\n**** STATION OUT OF RANGE ****")
;     (eval nil)
;    )
;   )
;  )
;  (progn
;   (princ "\n**** NO ALIGNMENT DEFINED ****")
;   (eval nil)
;  )
; )
;)
(defun GETRADIUS (STA / AL C DIR DIST R SIGN TOL)
 (setq TOL 0.00000001)
 (defun SIGN (X)
  (if (< X 0)
   (eval -1)
   (eval 1)
  )
 )
 (defun DIST (P1 P2 BULGE / ATOTAL CHORD R)
  (if (listp BULGE)
   (progn
    (- (GETSPIRALLS2 (car BULGE) (cadr BULGE) (caddr BULGE)) (cadddr BULGE))
   )
   (progn
    (setq ATOTAL (* 4.0 (atan (abs BULGE))))
    (setq CHORD (distance P1 P2))
    (if (= 0.0 BULGE)
     (eval CHORD)
     (progn 
      (setq R (/ CHORD (* 2 (sin (/ ATOTAL 2)))))
      (* R ATOTAL)
     )
    )
   )
  )
 )
 (if (/= nil ALIGNLIST)
  (progn
   (setq AL (last ALIGNLIST))
   (if (<= STA (+ (car AL) (DIST (cadr AL) (caddr AL) (cadddr AL))))
    (progn
     (setq C 0)
     (setq AL (nth C ALIGNLIST))
     (if (>= STA (car AL))
      (progn
       (while (> STA (+ (car AL) (DIST (cadr AL) (caddr AL) (cadddr AL))))
        (setq C (+ C 1))
        (setq AL (nth C ALIGNLIST))
       )
       (if (listp (cadddr AL))
        (progn
         (if (< (distance (caddr AL) (caddr (cadddr AL))) (distance (cadr AL) (caddr (cadddr AL))))
          (progn
           (setq R (GETSPIRALRADIUS (+ (- STA
                                          (car AL)
                                       )
                                       (cadddr (cadddr AL))
                                    )
                               (car (cadddr AL))
                               (cadr (cadddr AL))
                               (caddr (cadddr AL))
                   )
           )
          )
          (progn
           (setq R (* -1.0
                      (GETSPIRALRADIUS (- (GETSPIRALLS2 (car (cadddr AL))
                                                        (cadr (cadddr AL))
                                                        (caddr (cadddr AL))
                                          )
                                          (- STA
                                             (car AL)
                                          )
                                       )
                                       (car (cadddr AL))
                                       (cadr (cadddr AL))
                                       (caddr (cadddr AL))
                   )
                   )
           )
          )
         )
        )
        (progn
         (if (< (abs (cadddr AL)) TOL)
          (progn
           (setq R 0.0)
          )
          (progn
           (setq DIR (SIGN (cadddr AL)))
           (setq R (* DIR (RADIUS (cadr AL) (caddr AL) (cadddr AL))))
          )
         )
        )
       )
      )
      (progn
       (princ "\n**** STATION OUT OF RANGE ****")
       (eval nil)
      )
     )
    )
    (progn
     (princ "\n**** STATION OUT OF RANGE ****")
     (eval nil)
    )
   )
  )
  (progn
   (princ "\n**** NO ALIGNMENT DEFINED ****")
   (eval nil)
  )
 )
)
;(defun GETALIGNLENGTH (/ DIST)
; (defun DIST (P1 P2 BULGE / ATOTAL CHORD R)
;  (if (listp BULGE)
;   (progn
;    (- (GETSPIRALLS2 (car BULGE) (cadr BULGE) (caddr BULGE)) (cadddr BULGE))
;   )
;   (progn
;    (setq ATOTAL (* 4.0 (atan (abs BULGE))))
;    (setq CHORD (distance P1 P2))
;    (if (= 0.0 BULGE)
;     (eval CHORD)
;     (progn 
;      (setq R (/ CHORD (* 2 (sin (/ ATOTAL 2)))))
;      (* R ATOTAL)
;     )
;    )
;   )
;  )
; )
; (if (= ALIGNLIST nil)
;  (progn
;   (eval nil)
;  )
;  (progn
;   (- (+ (car (last ALIGNLIST))
;         (DIST (cadr (last ALIGNLIST)) (caddr (last ALIGNLIST)) (cadddr (last ALIGNLIST)))
;      )
;      (car (car ALIGNLIST))
;   )
;  )
; )
;)
