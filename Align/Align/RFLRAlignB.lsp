;
;
;   Program written by Robert Livingston, 2008/11/04
;
;   RFL:RALIGNB reads a horizontal alignment from a RFLAlign Block
;
;
(defun RFL:RALIGNB (BLKENT / ENT ENTLIST INLINE LO P1X P1Y P2X P2Y
                             PLTX PLTY PLTSTX PLTSTY PSTX PSTY BULGE)
 (setq RFL:ALIGNLIST nil)
 (setq ENT (entnext BLKENT))
 (setq ENTLIST (entget ENT))
 (while (/= "HOR" (cdr (assoc 2 ENTLIST)))
  (setq ENT (entnext ENT))
  (setq ENTLIST (entget ENT))
 )
 (setq INLINE (cdr (assoc 1 ENTLIST)))
 (setq ENT (entnext ENT))
 (setq ENTLIST (entget ENT))
 (if (/= INLINE "#RFL HORIZONTAL ALIGNMENT FILE")
  (progn
   (princ "\n*** FILE NOT FORMATTED CORRECTLY ***\n")
  )
  (progn
   (setq INLINE (cdr (assoc 1 ENTLIST)))
   (setq ENT (entnext ENT))
   (setq ENTLIST (entget ENT))
   (while (and (/= nil INLINE) (/= INLINE "#END DEFINITION"))
    (setq STA (atof INLINE))
    (setq INLINE (cdr (assoc 1 ENTLIST)))
    (setq ENT (entnext ENT))
    (setq ENTLIST (entget ENT))
    (setq P1X (atof INLINE))
    (setq INLINE (cdr (assoc 1 ENTLIST)))
    (setq ENT (entnext ENT))
    (setq ENTLIST (entget ENT))
    (setq P1Y (atof INLINE))
    (setq INLINE (cdr (assoc 1 ENTLIST)))
    (setq ENT (entnext ENT))
    (setq ENTLIST (entget ENT))
    (setq P2X (atof INLINE))
    (setq INLINE (cdr (assoc 1 ENTLIST)))
    (setq ENT (entnext ENT))
    (setq ENTLIST (entget ENT))
    (setq P2Y (atof INLINE))
    (setq INLINE (cdr (assoc 1 ENTLIST)))
    (setq ENT (entnext ENT))
    (setq ENTLIST (entget ENT))
    (if (= INLINE "SPIRAL")
     (progn
      (setq INLINE (cdr (assoc 1 ENTLIST)))
      (setq ENT (entnext ENT))
      (setq ENTLIST (entget ENT))
      (setq PLTX (atof INLINE))
      (setq INLINE (cdr (assoc 1 ENTLIST)))
      (setq ENT (entnext ENT))
      (setq ENTLIST (entget ENT))
      (setq PLTY (atof INLINE))
      (setq INLINE (cdr (assoc 1 ENTLIST)))
      (setq ENT (entnext ENT))
      (setq ENTLIST (entget ENT))
      (setq PLTSTX (atof INLINE))
      (setq INLINE (cdr (assoc 1 ENTLIST)))
      (setq ENT (entnext ENT))
      (setq ENTLIST (entget ENT))
      (setq PLTSTY (atof INLINE))
      (setq INLINE (cdr (assoc 1 ENTLIST)))
      (setq ENT (entnext ENT))
      (setq ENTLIST (entget ENT))
      (setq PSTX (atof INLINE))
      (setq INLINE (cdr (assoc 1 ENTLIST)))
      (setq ENT (entnext ENT))
      (setq ENTLIST (entget ENT))
      (setq PSTY (atof INLINE))
      (setq INLINE (cdr (assoc 1 ENTLIST)))
      (setq ENT (entnext ENT))
      (setq ENTLIST (entget ENT))
      (setq LO (atof INLINE))
      (setq BULGE (list (list PLTX PLTY) (list PLTSTX PLTSTY) (list PSTX PSTY) LO))
     )
     (progn
      (setq BULGE (atof INLINE))
     )
    )
    (setq INLINE (cdr (assoc 1 ENTLIST)))
    (setq ENT (entnext ENT))
    (setq ENTLIST (entget ENT))
    (setq RFL:ALIGNLIST (append RFL:ALIGNLIST (list (list STA (list P1X P1Y) (list P2X P2Y) BULGE))))
   )
  )
 )
)
