;
;
;     Program written by Robert Livingston, 2020-02-21
;
;     C:QUICKPROF is a utility for simulating vehicle and trailer profiles along a RFL vertical profile
;
;     Notes:
;
;            Profiles must be drawn at 1:1
;
;            Blocks must have the following attributes:
;                   DX : X distance from block insertion to rear wheels
;                   DY : Y distance from block insertion to rear wheels
;                   HX : X distance from block insertion to hitch point
;                   HY : Y distance from block insertion to hitch point
;
;            Blocks drawn from left to right
;
;
(defun C:QUICKPROF (/ *error* ANG ANGBASE ANGDIR BLOCKENTLIST BLOCKENTLISTSIM C CMDECHO D DIMLIST DIRFLAG DRAWLOADLINE DX DY ENT ENTLIST GETDIMS HX HY INC N0 N1 N2 NODE OSMODE P P0 PLIST PVILISTSAVE REP TMP VENTLIST)
;(defun C:QUICKPROF ()
 (setq CMDECHO (getvar "CMDECHO"))
 (setvar "CMDECHO" 0)
 (setq OSMODE (getvar "OSMODE"))
 (setvar "OSMODE" 0)
 (setq ANGBASE (getvar "ANGBASE"))
 (setvar "ANGBASE" 0.0)
 (setq ANGDIR (getvar "ANGDIR"))
 (setvar "ANGDIR" 0)

 (defun *error* (msg)
  (setq RFL:PVILIST PVILISTSAVE)
  (setvar "CMDECHO" CMDECHO)
  (setvar "OSMODE" OSMODE)
  (setvar "ANGBASE" ANGBASE)
  (setvar "ANGDIR" ANGDIR)
  (foreach ENT BLOCKENTLIST (redraw ENT 1))
  (foreach ENT BLOCKENTLISTSIM (entdel ENT))
  (print msg)
  nil
 )
 
 (defun DRAWLOADLINE (PLIST / ANG C D ENT H P1 P2 PREVENT S)
  (setq PREVENT nil)
  (if (setq D (getdist "\nEnter load length : "))
   (if (setq H (getdist "\nEnter load height : "))
    (if (setq S (getdist "\nEnter step size : "))
     (progn
      (while PLIST
       (setq C 0)
       (while (and (< C (length PLIST)) (< (distance (car PLIST) (nth C PLIST)) D))
        (setq C (1+ C))
       )
       (if (< C (length PLIST))
        (progn
         (setq ANG (angle (car PLIST) (nth C PLIST)))
         (setq P1 (list (- (car (car PLIST)) (* H (sin ANG)))
                        (+ (cadr (car PLIST)) (* H (cos ANG)))
                  )
         )
         (setq P2 (list (- (car (nth C PLIST))(* H (sin ANG)))
                        (+ (cadr (nth C PLIST))(* H (cos ANG)))
                  )
         )
         (entmake (list (cons 0 "LINE")
                        (cons 10 P1)
                        (cons 11 P2)
                  )
         )
         (setq ENT (entlast))(RFL:PUTPREVENT ENT PREVENT)(RFL:PUTNEXTENT PREVENT ENT)(setq PREVENT ENT)
        )
        (setq PLIST nil)
       )
       (setq P1 (car PLIST))
       (while (and PLIST (< (distance P1 (car PLIST)) S))
        (setq PLIST (cdr PLIST))
       )
      )
     )
    )
   )
  )
 )
 
 (defun GETDIMS (ENT / ENT2 ENTLIST)
  (if (= (cdr (assoc 66 (entget ENT))) 1)
   (progn
    (setq ENT2 (entnext ENT))
    (setq ENTLIST (entget ENT2))
    (while (= (cdr (assoc 0 ENTLIST)) "ATTRIB")
     (cond ((and (= (cdr (assoc 2 ENTLIST)) "DX") (/= (cdr (assoc 1 ENTLIST)) "")) (setq DX (atof (cdr (assoc 1 ENTLIST)))))
           ((and (= (cdr (assoc 2 ENTLIST)) "DY") (/= (cdr (assoc 1 ENTLIST)) "")) (setq DY (atof (cdr (assoc 1 ENTLIST)))))
           ((and (= (cdr (assoc 2 ENTLIST)) "HX") (/= (cdr (assoc 1 ENTLIST)) "")) (setq HX (atof (cdr (assoc 1 ENTLIST)))))
           ((and (= (cdr (assoc 2 ENTLIST)) "HY") (/= (cdr (assoc 1 ENTLIST)) "")) (setq HY (atof (cdr (assoc 1 ENTLIST)))))
     )
     (setq ENT2 (entnext ENT2))
     (setq ENTLIST (entget ENT2))
    )
    (if (and DX DY) T nil)
   )
   nil
  )
 )
 
 (setq INC 0.1)
 
 (if (setq ENT (car (setq P (entsel "\nSelect ground polyline (near to start) : "))))
  (if (or (= (cdr (assoc 0 (setq ENTLIST (entget ENT)))) "POLYLINE")
          (= (cdr (assoc 0 ENTLIST)) "LWPOLYLINE")
      )
   (progn
    (setq P (cadr P))
    (if (setq PLIST (RFL:GETPLISTINC P INC ENT))
     (progn
      (if (< (caar PLIST) (car (last PLIST)))
       (setq DIRFLAG "F")
       (setq DIRFLAG "R")
      )
      (setq DIMLIST nil)
      (setq BLOCKENTLIST nil)
      (setq BLOCKENTLISTSIM nil)
      (setq HX T HY T)
      (while (and HX HY (setq ENT (car (entsel "\nSelect vehicle (front to rear) : "))))
       (setq DX nil DY nil HX nil HY nil)
       (if (GETDIMS ENT)
        (progn
         (setq BLOCKENTLIST (append BLOCKENTLIST (list ENT)))
         (redraw ENT 2)
         (setq ENT (RFL:MAKETEMPBLOCK ENT))
         (setq BLOCKENTLISTSIM (append BLOCKENTLISTSIM (list ENT)))
         (redraw ENT 2)
         (setq DIMLIST (append DIMLIST (list (list DX DY HX HY))))
        )
       )
      )
      (setq P0 (getpoint "\nPick start point for simulation : "))
      (setq P0 (list (car P0) (cadr P0)))
      (setq N0 0)
      (setq P (nth N0 PLIST))
      (while (and (< (1+ N0) (length PLIST)) (< (distance (nth (1+ N0) PLIST) P0) (distance P P0)))
       (setq N0 (1+ N0) P (nth N0 PLIST))
      )
      (foreach ENT BLOCKENTLISTSIM (redraw ENT 1))
      (setq REP "XXX")
      (setq N1 N0)
      (setq TMP "Next")
      (while (/= (strcase REP) "EXIT")
       (setq P (nth N0 PLIST))
       (setq N1 N0)
       (setq C 0)
       (while (< C (length DIMLIST))
        (setq ENT (nth C BLOCKENTLISTSIM))
        (setq DX (nth 0 (nth C DIMLIST)))
        (setq DY (nth 1 (nth C DIMLIST)))
        (setq HX (nth 2 (nth C DIMLIST)))
        (setq HY (nth 3 (nth C DIMLIST)))
        (setq D (sqrt (+ (* DX DX) (* DY DY))))
        (setq ANG (angle (list 0.0 0.0) (list DX DY)))
        (setq N2 N1)
        (while (and (> N2 0) (< (distance P (nth N2 PLIST)) D))
         (setq N2 (1- N2))
        )
        (setq ENTLIST (entget ENT))
        (setq ENTLIST (subst (cons 10 P)
                             (assoc 10 ENTLIST)
                             ENTLIST
                      )
        )
        (if (= DIRFLAG "F")
         (setq ENTLIST (subst (cons 50 (setq ANG (+ (angle P (nth N2 PLIST)) ANG)))
                              (assoc 50 ENTLIST)
                              ENTLIST
                       )
         )
         (setq ENTLIST (subst (cons 50 (setq ANG (- (angle P (nth N2 PLIST)) ANG)))
                              (assoc 50 ENTLIST)
                              ENTLIST
                       )
         )
        )
        (if (= DIRFLAG "F")
         (setq ENTLIST (subst (cons 42 -1.0)
                              (assoc 42 ENTLIST)
                              ENTLIST
                       )
         )
        )
        (entmod ENTLIST)
        (entupd ENT)
        (if (and HX HY)
         (if (= DIRFLAG "F")
          (setq P (list (- (car P) (- (* HX (cos (- pi ANG))) (* HY (sin (- pi ANG)))))
                        (+ (cadr P) (+ (* HX (sin (- pi ANG))) (* HY (cos (- pi ANG)))))
                  )
          )
          (setq P (list (+ (car P) (- (* HX (cos ANG)) (* HY (sin ANG))))
                        (+ (cadr P) (+ (* HX (sin ANG)) (* HY (cos ANG))))
                  )
          )
         )
        )
        (setq N1 N2)
        (setq C (1+ C))
       )
       (initget "Draw Move Next Prev Copy Exit eXit")
       (setq REP (getkword (strcat "\nNext / Prev / Move / Copy / Exit / Drawloadlines <" TMP "> : ")))
       (if (= REP nil) (setq REP TMP))
       (cond ((= REP "Next") (setq N0 (min (1+ N0) (1- (length PLIST)))
                                   TMP "Next"
                             )
             )
             ((= REP "Prev") (setq N0 (max (1- N0) 0)
                                   TMP "Prev"
                             )
             )
             ((= REP "Move")
              (progn
               (setq P0 (getpoint "\nPick point for simulation : "))
               (setq P0 (list (car P0) (cadr P0)))
               (setq N0 0)
               (setq P (nth N0 PLIST))
               (while (and (< (1+ N0) (length PLIST)) (< (distance (nth (1+ N0) PLIST) P0) (distance P P0)))
                (setq N0 (1+ N0) P (nth N0 PLIST))
               )
              )
             )
             ((= REP "Copy") (foreach NODE BLOCKENTLISTSIM (RFL:MAKETEMPBLOCK NODE)))
             ((= REP "Draw") (DRAWLOADLINE PLIST))
       )
       
      )
     )
    )
   )
  )
 )
 (setq RFL:PVILIST PVILISTSAVE)
 (setvar "CMDECHO" CMDECHO)
 (setvar "OSMODE" OSMODE)
 (setvar "ANGBASE" ANGBASE)
 (setvar "ANGDIR" ANGDIR)
 (foreach ENT BLOCKENTLIST (redraw ENT 1))
 (foreach ENT BLOCKENTLISTSIM (entdel ENT))
 T
)
