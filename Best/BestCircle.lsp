(defun C:BESTCIRCLE (/ C ENT ENT2 ENTLIST ENTSET P PLIST)
 (setq PLIST nil)
 (setq ENTSET (ssget))
 (setq C 0)
 (while (< C (sslength ENTSET))
  (setq ENT (ssname ENTSET C))
  (setq ENTLIST (entget ENT))
  (if (= (cdr (assoc 0 ENTLIST)) "POINT")
   (setq PLIST (append PLIST (list (cdr (assoc 10 ENTLIST)))))
   (if (= "LWPOLYLINE" (cdr (assoc 0 ENTLIST)))
    (while (/= nil ENTLIST)
     (if (= 10 (caar ENTLIST))
       (setq PLIST (append PLIST (list (cdar ENTLIST))))
     )
     (setq ENTLIST (cdr ENTLIST))
    )
    (if (= "POLYLINE" (cdr (assoc 0 ENTLIST)))
     (progn
      (setq ENT (entnext ENT))
      (setq ENTLIST (entget ENT))
      (while (= "VERTEX" (cdr (assoc 0 ENTLIST)))
       (setq P (cdr (assoc 10 ENTLIST)))
       (setq PLIST (append PLIST (list (list (car P) (cadr P)))))
       (setq ENT (entnext ENT))
       (setq ENTLIST (entget ENT))
      )
     )
    )
   )
  )
  (setq C (+ C 1))
 )
 (if (/= nil (setq P (BESTCIRCLE PLIST)))
  (command "._CIRCLE" "NON" (car P) (cadr P))
 )
)
(defun BESTCIRCLE (PLIST / C CALCE COMBLIST COUNT E P PC PCT NODE R RT STEP SUME2 SUME2T SUME2T1 SUME2T2 SUME2T3 SUME2T4 SUME2T5 SUME2T6 TOL)
;(defun BESTCIRCLE (PLIST)
 (setq TOL 0.00001)
 (defun CALCSUME2 (PC R PLIST / SUME2 NODE)
  (setq SUME2 0.0)
  (foreach NODE PLIST
   (setq SUME2 (+ SUME2 (expt (abs (- (distance PC NODE) R)) 2)))
  )
  (eval SUME2)
 )
 (defun CALCE (PC R PLIST / E NODE TMP)
  (setq E nil)
  (foreach NODE PLIST
   (progn
    (setq TMP (abs (- (distance PC NODE) R)))
    (if (= E nil)
     (setq E TMP)
     (if (> TMP E) (setq E TMP))
    )
   )
  )
  (eval E)
 )
 (if (= nil (listp PLIST))
  (eval nil)
  (if (< (length PLIST) 3)
   (eval nil)
   (if (= (length PLIST) 3)
    (if (= nil (setq PC (RFL:CIRCLE3P (car PLIST) (cadr PLIST) (caddr PLIST))))
     (eval nil)
     (append PC (list 0.0))
    )
    (progn
     (setq C 0)
     (setq PC nil)
     (setq R 0.0)
     (if (> (length PLIST) 8)
      (setq COMBLIST (list (list 1 (/ (length PLIST) 2) (length PLIST))))
      (setq COMBLIST (COMB3 (length PLIST)))
     )
     (foreach NODE COMBLIST
      (progn
       (if (/= nil (setq P (RFL:CIRCLE3P (nth (- (car NODE) 1) PLIST) (nth (- (cadr NODE) 1) PLIST) (nth (- (caddr NODE) 1) PLIST))))
        (progn
         (setq C (+ C 1))
         (if (= nil PC)
          (setq PC (car P))
          (setq PC (list (+ (car PC) (caar P)) (+ (cadr PC) (cadar P))))
         )
         (setq R (+ R (cadr P)))
        )
       )
      )
     )
     (if (= C 0)
      (eval nil)
      (progn
       (setq PC (list (/ (car PC) C) (/ (cadr PC) C)))
       (setq R  (/ R C))
       ; REGRESSION
       (setq COUNT 0)
       (setq STEP R)
       (setq SUME2 (CALCSUME2 PC R PLIST))
       (while (> STEP TOL)
        (setq RT (+ R STEP))
        (setq PCT PC)
        (setq SUME2T1 (CALCSUME2 PCT RT PLIST))
        (setq RT (- R STEP))
        (setq PCT PC)
        (setq SUME2T2 (CALCSUME2 PCT RT PLIST))
        (setq RT R)
        (setq PCT (list (+ (car PC) STEP) (cadr PC)))
        (setq SUME2T3 (CALCSUME2 PCT RT PLIST))
        (setq RT R)
        (setq PCT (list (- (car PC) STEP) (cadr PC)))
        (setq SUME2T4 (CALCSUME2 PCT RT PLIST))
        (setq RT R)
        (setq PCT (list (car PC) (+ (cadr PC) STEP)))
        (setq SUME2T5 (CALCSUME2 PCT RT PLIST))
        (setq RT R)
        (setq PCT (list (car PC) (- (cadr PC) STEP)))
        (setq SUME2T6 (CALCSUME2 PCT RT PLIST))
        (setq SUME2 (min SUME2 SUME2T1 SUME2T2 SUME2T3 SUME2T4 SUME2T5 SUME2T6))
        (cond ((= SUME2 SUME2T1) (setq R (+ R STEP)))
              ((= SUME2 SUME2T2) (setq R (- R STEP)))
              ((= SUME2 SUME2T3) (setq PC (list (+ (car PC) STEP) (cadr PC))))
              ((= SUME2 SUME2T4) (setq PC (list (- (car PC) STEP) (cadr PC))))
              ((= SUME2 SUME2T5) (setq PC (list (car PC) (+ (cadr PC) STEP))))
              ((= SUME2 SUME2T6) (setq PC (list (car PC) (- (cadr PC) STEP))))
              (T (setq STEP (/ STEP 2.0)))
        )
        (setq COUNT (+ COUNT 1))(if (= 10000 COUNT) (exit))
       )
       ; END REGRESSION
       (list PC R (CALCE PC R PLIST))
      )
     )
    )
   )
  )
 )
)
