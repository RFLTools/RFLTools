(defun C:BESTVCURVE (/ C D1 D2 ENT ENTLIST FLAG NODE P P1 P2 P3 OSMODE PLIST PLISTTMP PLINETYPE SPLINESEGS SPLINETYPE)
 (setq OSMODE (getvar "OSMODE"))
 (setvar "OSMODE" 0)
 (setq SPLINETYPE (getvar "SPLINETYPE"))
 (setvar "SPLINETYPE" 5)
 (setq SPLINESEGS (getvar "SPLINESEGS"))
 (setvar "SPLINESEGS" 65)
 (setq PLINETYPE (getvar "PLINETYPE"))
 (setvar "PLINETYPE" 0)
 (setq PLIST nil)
 (setq ENT (car (entsel "\nSelect polyline to fit parabolic vertical curve : ")))
 (setq ENTLIST (entget ENT))
 (if (= "LWPOLYLINE" (cdr (assoc 0 ENTLIST)))
  (while (/= nil ENTLIST)
   (if (= 10 (caar ENTLIST))
    (setq PLIST (append PLIST (list (cdar ENTLIST))))
   )
   (setq ENTLIST (cdr ENTLIST))
  )
  (if (= "POLYLINE" (cdr (assoc 0 ENTLIST)))
   (progn
    (setq ENT (entnext ENT))
    (setq ENTLIST (entget ENT))
    (while (= "VERTEX" (cdr (assoc 0 ENTLIST)))
     (setq P (cdr (assoc 10 ENTLIST)))
     (setq PLIST (append PLIST (list (list (car P) (cadr P)))))
     (setq ENT (entnext ENT))
     (setq ENTLIST (entget ENT))
    )
   )
   (princ "\n*** Not a polyline!")
  )
 )
 (if (/= nil (setq P1 (getpoint "\nPick a point near to start point (<return> for entire polyline) : ")))
  (if (/= nil (setq P2 (getpoint "\nPick a point near to end point : ")))
   (progn
    (setq PLISTTMP nil)
    (setq FLAG nil)
    (setq D1 (apply 'min (mapcar '(lambda (P3) (distance P1 P3)) PLIST)))
    (setq D2 (apply 'min (mapcar '(lambda (P3) (distance P2 P3)) PLIST)))
    (foreach P3 PLIST
     (progn
      (if (or (= D1 (distance P1 P3)) (= D2 (distance P2 P3)))
       (setq FLAG (not FLAG))
      )
      (if FLAG (setq PLISTTMP (append PLISTTMP (list P3))))
     )
    )
    (setq PLIST PLISTTMP)
   )
  )
 )
 (if (/= nil (setq P (BESTVCURVE PLIST)))
  (progn
   (setq P1 (car P))
   (setq P2 (cadr P))
   (setq P3 (caddr P))
   (command "._PLINE" P1 P2 P3 "")
   (command "._PEDIT" (entlast) "S" "")
  )
 )
 (setvar "OSMODE" OSMODE)
 (setvar "SPLINETYPE" SPLINETYPE)
 (setvar "SPLINESEGS" SPLINESEGS)
 (setvar "PLINETYPE" PLINETYPE)
 (last P)
)
(defun BESTVCURVE (PLIST / CALCE CALCSUME2 COUNT P1 P2 P3 TOL)
 (setq TOL 0.00001)
 (defun CALCE (P1 P2 P3 PLIST / A B C G1 G2 NODE Y YMAX)
  (setq YMAX nil)
  (setq G1 (/ (- (cadr P2) (cadr P1)) (- (car P2) (car P1))))
  (setq G2 (/ (- (cadr P3) (cadr P2)) (- (car P3) (car P2))))
  (setq A (/ (- G2 G1) (* 2.0 (- (car P3) (car P1)))))
  (setq B (- G1 (* 2.0 A (car P1))))
  (setq C (- (cadr P1) (* A (car P1) (car P1)) (* B (car P1))))
  (foreach NODE PLIST
   (setq Y (+ (* A (car NODE) (car NODE)) (* B (car NODE)) C))
   (if (= nil YMAX)
    (setq YMAX (abs (- (cadr NODE) Y)))
    (if (> (abs (- (cadr NODE) Y)) YMAX)
     (setq YMAX (abs (- (cadr NODE) Y)))
    )
   )
  )
  (eval YMAX)
 )
 (defun CALCSUME2 (P1 P2 P3 PLIST / A B C G1 G2 NODE PT STEP SUME2 SUME2T1 SUME2T2 SUME2T3 SUME2T4 SUME2T5 SUME2T6 Y)
  (setq SUME2 0.0)
  (setq G1 (/ (- (cadr P2) (cadr P1)) (- (car P2) (car P1))))
  (setq G2 (/ (- (cadr P3) (cadr P2)) (- (car P3) (car P2))))
  (setq A (/ (- G2 G1) (* 2.0 (- (car P3) (car P1)))))
  (setq B (- G1 (* 2.0 A (car P1))))
  (setq C (- (cadr P1) (* A (car P1) (car P1)) (* B (car P1))))
  (foreach NODE PLIST
   (setq Y (+ (* A (car NODE) (car NODE)) (* B (car NODE)) C))
   (setq SUME2 (+ SUME2 (expt (abs (- (cadr NODE) Y)) 2)))
  )
  (eval SUME2)
 )
 (if (< (length PLIST) 3)
  (eval nil)
  (progn
   (if (> (caar PLIST) (car (last PLIST))) (setq PLIST (reverse PLIST)))
   (setq COUNT 0)
   (setq P1 (car PLIST))
   (setq P3 (last PLIST))
   (setq P2 (list (/ (+ (car P1) (car P3)) 2.0) (/ (+ (cadr P1) (cadr P3)) 2.0)))
   (setq STEP (- (car P3) (car P1)))
   (setq SUME2 (CALCSUME2 P1 P2 P3 PLIST))
   (while (> STEP TOL)
    (setq PT (list (car P1) (+ (cadr P1) STEP)))
    (setq SUME2T1 (CALCSUME2 PT P2 P3 PLIST))
    (setq PT (list (car P1) (- (cadr P1) STEP)))
    (setq SUME2T2 (CALCSUME2 PT P2 P3 PLIST))
    (setq PT (list (car P2) (+ (cadr P2) STEP)))
    (setq SUME2T3 (CALCSUME2 P1 PT P3 PLIST))
    (setq PT (list (car P2) (- (cadr P2) STEP)))
    (setq SUME2T4 (CALCSUME2 P1 PT P3 PLIST))
    (setq PT (list (car P3) (+ (cadr P3) STEP)))
    (setq SUME2T5 (CALCSUME2 P1 P2 PT PLIST))
    (setq PT (list (car P3) (- (cadr P3) STEP)))
    (setq SUME2T6 (CALCSUME2 P1 P2 PT PLIST))
    (setq SUME2 (min SUME2 SUME2T1 SUME2T2 SUME2T3 SUME2T4 SUME2T5 SUME2T6))
    (cond ((= SUME2 SUME2T1) (setq P1 (list (car P1) (+ (cadr P1) STEP))))
          ((= SUME2 SUME2T2) (setq P1 (list (car P1) (- (cadr P1) STEP))))
          ((= SUME2 SUME2T3) (setq P2 (list (car P2) (+ (cadr P2) STEP))))
          ((= SUME2 SUME2T4) (setq P2 (list (car P2) (- (cadr P2) STEP))))
          ((= SUME2 SUME2T5) (setq P3 (list (car P3) (+ (cadr P3) STEP))))
          ((= SUME2 SUME2T6) (setq P3 (list (car P3) (- (cadr P3) STEP))))
          (T (setq STEP (/ STEP 2.0)))
    )
    (setq COUNT (+ COUNT 1))(if (= 10000 COUNT) (exit))
   )
   (list P1 P2 P3 (CALCE P1 P2 P3 PLIST))
  )
 )
)
